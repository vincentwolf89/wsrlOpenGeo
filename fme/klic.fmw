FME workspace klic.fmw

Creator
    GEOMTYPE = Geometry Object
    NUM = 1
    CREATED -> KLIC_Transformer [Creation_instance]
KLIC_Transformer: KLIC Transformer
    Destination_writer = C:\Users\vince\Desktop\klic\output
    KLIC_FOLDER = C:\Users\vince\Desktop\klic\KLIC Zuidelijke Waaldijken
    KLIC_style_GPKG = $(FME_MF_DIR)KLIC Styling_V2.gpkg
    Output_raw -> AttributeCreator
AttributeCreator
    ATTR_TABLE = SET_TO _ouput_filename (varchar(200)) = C:\Users\vince\Desktop\klic\output\gis\@Value(fme_feature_type).geojson
    -> FeatureWriter [Output_raw]
FeatureWriter
    COORDSYS = EPSG:28992
    DATASET = @Value(_ouput_filename)
    DATASET_ATTR = _dataset
    FEATURE_TYPE_LIST_ATTR = _feature_types
    FORMAT = GEOJSON
    GEOJSON_COUNTER_CLOCKWISE_AREAS = Yes
    GEOJSON_DESTINATION_DATASETTYPE_VALIDATION = Yes
    GEOJSON_FILE_STRUCTURE = SINGLE_FEATURE_COLLECTION
    GEOJSON_INDENT_SIZE = 0
    GEOJSON_MAX_COORDINATE_PRECISION = 10
    GEOJSON_PRETTY_PRINT = YES
    GEOJSON_WGS84_REPROJECTION = Yes
    GEOJSON_WRITER_CHARSET = UTF-8
    GEOJSON_WRITE_BOM = No
    GROUP_BY = fme_feature_type
    TOTAL_FEATURES_WRITTEN_ATTR = _total_features_written

FME custom transformer SchemaSetter
This transformer adds both exposed and unexposed attributes to a feature-based schema, with appropriate data types. 
For example: if a feature has the following attributes:
Attribute(boolean) : 'mybool' has value 'Yes' 
Attribute(32 bit integer): 'myint' has value '12' 
Attribute(64 bit real) : 'myreal' has value '12.965' 
the following list attributes will be added:
Attribute(string) : 'attribute{0}.fme_data_type' has value 'fme_boolean' 
Attribute(encoded: utf-8): 'attribute{0}.name' has value 'mybool' 
Attribute(string) : 'attribute{1}.fme_data_type' has value 'fme_int32' 
Attribute(encoded: utf-8): 'attribute{1}.name' has value 'myint' 
Attribute(string) : 'attribute{2}.fme_data_type' has value 'fme_real64' 
Attribute(encoded: utf-8): 'attribute{2}.name' has value 'myreal' 
The transformer also gives users the option to exclude certain attributes based on name or prefix, and automatically excludes all "fme_" attributes.  Another option exists to force all attributes to string data type in the case of mismatches in the source attributes.
Input Ports 
Features containing attributes for which a schema definition is required. 
Output Ports 
All features are output. Attributes which have been selected to be excluded are removed from the feature. The list containing the schema of the feature is added to each feature. 
Parameters 
Attributes to Exclude 
A selected set of attributes that will be excluded from the generated schema list and removed from the feature.
Prefixes to Exclude 
A comma-delimited list of prefixes for attributes that are to be excluded from the generated schema list and removed from the feature. Regular expressions are not supported. For example: "date" will exclude any attributes that start with the letters "date" e.g. date_created, dateupdated
Sort Attributes 
(Ascending, Descending, None) Set this parameter to alphabetically sort output attributes.
Force attributes to strings:
If set to "No", the SchemaSetter will set the data type to the native attribute data type. If set to "Yes", the SchemaSetter will force all attribute data type sto "fme_char(255)".
Usage Notes 
The feature based schema can be passed to any writer that it set to Dynamic Mode and used with the "Schema from First Feature" setting.
Please see https://knowledge.safe.com/articles/1051/dynamic-workflow-tutorial-destination-schema-is-de-2.html for more information on feature-based schema using list attributes.

Parameters:
- AttributesToExclude =   # " " Attributes to exclude
- PrefixesToExclude =   # Prefixes to exclude
- SORT = None   # Sort Attributes
- ForceDataType = No   # Force attributes to strings?

Input_2 (input)
    -> ParameterFetcher
Note: Retrieve Parameters
ParameterFetcher
    ATTR_LIST = _AttributesToExclude $(AttributesToExclude) _PrefixesToExclude $(PrefixesToExclude) _sort $(SORT) _ForceDataType $(ForceDataType)
    -> PythonCaller
Note: See Comment in Code
PythonCaller
    PYTHONSOURCE:
      from __future__ import absolute_import, division, print_function, unicode_literals

      import fmeobjects
      import six

      #Checks if a list entry starts with a certain string
      def StringLikeList(list,string):
              test=False
              for element in list:
                  if string.startswith(element):
                      test=True
              return test

       # Checks if a list contains an element equal to a certain string
      def StringInList(list,string):
              test=False
              for element in list:
                  if string==element:
                      test=True
              return test

      # Template Class Interface:
      class FeatureProcessor(object):

          typesMapping = {
              fmeobjects.FME_ATTR_UNDEFINED : None,
              fmeobjects.FME_ATTR_BOOLEAN : "fme_boolean",
              fmeobjects.FME_ATTR_INT8 : "fme_int8",
              fmeobjects.FME_ATTR_UINT8 : "fme_uint8",
              fmeobjects.FME_ATTR_INT16 : "fme_int16",
              fmeobjects.FME_ATTR_UINT16 : "fme_uint16",
              fmeobjects.FME_ATTR_INT32 : "fme_int32",
              fmeobjects.FME_ATTR_UINT32 : "fme_uint32",
              fmeobjects.FME_ATTR_REAL32 : "fme_real32",
              fmeobjects.FME_ATTR_REAL64 : "fme_real64",
              fmeobjects.FME_ATTR_REAL80 : "fme_real80",
              fmeobjects.FME_ATTR_STRING : "fme_char(255)",
              fmeobjects.FME_ATTR_ENCODED_STRING : "fme_varchar(255)",
              fmeobjects.FME_ATTR_INT64 : "fme_int64",
              fmeobjects.FME_ATTR_UINT64 : "fme_uint64"
           }

          def __init__(self):
              pass
          def input(self,feature):
              #create a new feature
              nfeature=fmeobjects.FMEFeature()
              #get list of all attributes on feature
              attlist=feature.getAllAttributeNames()
              #loop through all attributes and add to schema if they fail exclusion criteria
              i=0
              ExcludedAttributes=str(feature.getAttribute('_AttributesToExclude')).split(",")
              ExcludedAttributes.append('_ForceDataType')
              ExcludedPrefixes=str(feature.getAttribute('_PrefixesToExclude')).split(",")

              # remove all fme_ attributes from list - don't want to include these in dynamic schema
              ExcludedPrefixes = ['fme_'] if ExcludedPrefixes == [''] else ExcludedPrefixes + ["fme_"]

              # sorting attributes
              if feature.getAttribute('_sort') == 'Ascending' or feature.getAttribute('_sort') == 'Descending':
                  attlist.sort()
                  if feature.getAttribute('_sort') == 'Descending':
                      attlist.reverse()

              for att in attlist:
                  if not StringInList(ExcludedAttributes,att) and not StringLikeList(ExcludedPrefixes,att) and not att=='_AttributesToExclude' and not att=='_PrefixesToExclude' and not att=='_sort':

                     #Check datatype and set in schema
                     if feature.getAttribute('_ForceDataType') == 'No':
                         type = feature.getAttributeType(att)
                         type = self.typesMapping[type]
                     #Force to string if user wishes
                     else:
                         type = "fme_char(255)"

                     if type is None:
                         feature.removeAttribute(att)
                     else:
                         #add schema attributes to feature
                         nfeature.setAttribute("attribute{"+str(i)+"}.fme_data_type",type)
                         nfeature.setAttribute("attribute{"+str(i)+"}.name",six.text_type(att))
                         nfeature.setAttribute(att,feature.getAttribute(att))
                         i+=1;
              #copy original geometry to new feature
              nfeature.setGeometry(feature.getGeometry())
              nfeature.setCoordSys(feature.getCoordSys())
              nfeature.setFeatureType(feature.getFeatureType())
              nfeature.setAttribute("fme_geometry{0}",feature.getAttribute("fme_type"))
              nfeature.setAttribute("fme_feature_type",feature.getAttribute("fme_feature_type"))
              print(i)
              self.pyoutput(nfeature)
          def close(self):
              pass
    PYTHONSYMBOL = FeatureProcessor
    -> Output_2 (output)
Output_2 (output)

FME custom transformer KLIC Transformer
KLIC Transformer (version 2)
By: Vos Geo-analyses (Roelof Vos)
This free KLIC Transformer reads a previously downloaded KLIC file. The KLIC is downloaded from Kadaster.nl and shows all cables and pipelines in the specified area.
The goal of this transformer is to read the .xml file, connect and expose all relevant data to each geometry and write it with a pre-defined style to a GeoPackage, or provide it to the end user as a raw output.
Input
Use a Creator with one creation instance to kick off the transformer.
The KLIC file can be zipped or unzipped. The transformer can also process unzipped files within the same folder. KLIC files must begin with the name "Levering_". 
User parameters
The KLIC transformer works with three user parameters: 
1. KLIC_FOLDER: specify where you saved your KLIC downloads on your computer. From here the transformer will load all data with a Directory and File Pathnames reader. 
2. Destination_writer: Specify where you want the styled GeoPackge to be written to. 
3. KLIC_style_GPKG: Specify where you have saved the styling GeoPackage. This GeoPackage can be obtained via an email to roelof@vosgeo-analyses.nl or via this download link: "https://vosgeo-analyses.nl/assets/KLIC%20Styling_V2.gpkg". This GeoPackage is required to automatically provide styling for your output KLIC.
Output
A raw output port is provided to the user to continue with their KLIC data within FME. 
A Geopackage writer is used to write off the pre-styled KLIC. The location where this Geopackage is stored is provided by the user via user parameters and is returned to the user via the output port "Output_location_styled".
Use notes:
The KLIC transformer can encounter inconsistencies within the KLIC data. The script uses Warning Loggers to provide user feedback regarding these inconsistencies. Examples include non-matches related to beheerder-netwerk matching, K&L matching with netwerk, etc. These types of warnings are not fatal, but users are advised to review them.
Non-matches on IDs may also occur within the UtilityLink geometries. These are written as fme_feature_type "UtilityLink"
The GeoPackage writer uses a template GeoPackage that is pre-styled, allowing users to work with a ready-to-use file in their GIS system. A raw output port is also available for further use in FME.
Use of this transformer is at your own risk. Vos Geo-Analyses cannot be held responsible for any errors in the script.
The use of KLIC Transformer is free of use. Reselling of the KLIC Transformer is not allowed.
Credits:
Without the help of others I couldn't have published this transformer. Thanks to:
Annika van den Boom (Stantec): for helping me brainstorm with certain data-issues
Koen Verhoeven (Terralytics): for helping me optimize my script and provide all-round feedback.
Hans van der Maarel (Red Geographics): for helping me troubleshoot with the .fmx.
For help, questions and/or feedback, feel free to reach out. I'd love to hear from you.
Roelof@vosgeo-analyses.nl

Parameters:
- KLIC_FOLDER =   # Selecter the folder where the KLIC is located
- KLIC_style_GPKG =   # "" Select the KLIC_Style Geopackage
- Destination_writer =   # Select destination where to write

Note: Expose kabel of leiding waarde
Junction_2
    -> AttributeExposer_5
Note: nominaal voltage, operationeel voltage, pijp diameter, / atmosferische druk
AttributeExposer_5
    ATTR_LIST = link{}.xlink_href,inspireId.Identifier.namespace,nominalVoltage,nominalVoltage.uom,operatingVoltage,operatingVoltage.uom,pipeDiameter,pipeDiameter.uom,pressure,pressure.uom,beginLifespanVersion,validFrom,validTo,verticalPosition,label,warningType.xlink_href,currentStatus.xlink_href
    -> StringReplacer_6
Note: EV's mergen met bronhouders
FeatureMerger_7
    ATTR_ACCUM_MODE = Merge Supplier
    ATTR_CONFLICT_RES_LOOKUP = REQUESTOR_IF_CONFLICT
    GROUP_BY = path_filename
    IGNORE_NULLS = No
    JOIN_KEYS = @Value(BeheerderCode) @Value(BeheerderCode) AUTO
    MERGE_TYPE = Attributes and Geometry
    PRESERVE_FEATURE_ORDER_LOOKUP = PER_OUTPUT_PORT
    PROCESS_DUPS = NO
    REJECT_NULL_MISSING_KEYS = No
    SUPPLIERS_FIRST = No
    ATTR_CONFLICT_RES = Use Requestor
    MERGED -> GeometryValidator
GeometryValidator
    ISSUE_ATTR_NAME = _issues
    PRESETS = All
    REPAIR = Yes
    RULES = AREA_ORIENTATION AREA_ORIENTATION]VALID]FME_CONTROLLER_QUERY_FILE]transformers/dependencies/geometryvalidator8/AREA_ORIENTATION.fme]FME_CONTROLLER_CHOICE]AREA_ORIENTATION CONSECUTIVE_IDENTICAL_VERTICES_2D CHECK_Z]YES]TOLERANCE]0.0]FME_CONTROLLER_QUERY_FILE]transformers/dependencies/geometryvalidator8/CONSECUTIVE_IDENTICAL_VERTICES_2D.fme]FME_CONTROLLER_CHOICE]CONSECUTIVE_IDENTICAL_VERTICES_2D MISSING_TEXTURE_COORDINATES FME_CONTROLLER_QUERY_FILE]transformers/dependencies/geometryvalidator8/MISSING_TEXTURE_COORDINATES.fme]FME_CONTROLLER_CHOICE]MISSING_TEXTURE_COORDINATES MISSING_VERTEX_NORMALS FME_CONTROLLER_QUERY_FILE]transformers/dependencies/geometryvalidator8/MISSING_VERTEX_NORMALS.fme]FME_CONTROLLER_CHOICE]MISSING_VERTEX_NORMALS NAN_REMOVAL PROCESS_MEASURE]NO]FME_CONTROLLER_QUERY_FILE]transformers/dependencies/geometryvalidator8/NAN_REMOVAL.fme]FME_CONTROLLER_CHOICE]NAN_REMOVAL NULL_REMOVAL FME_CONTROLLER_QUERY_FILE]transformers/dependencies/geometryvalidator8/NULL_REMOVAL.fme]FME_CONTROLLER_CHOICE]NULL_REMOVAL OGC_VALID_CHECK OGC_VERSION]V1.2.0]LEGACY_OGC]No]FME_CONTROLLER_QUERY_FILE]transformers/dependencies/geometryvalidator8/OGC_VALID_CHECK.fme]FME_CONTROLLER_CHOICE]OGC_VALID_CHECK OGC_SIMPLE_CHECK LEGACY_OGC]No]FME_CONTROLLER_QUERY_FILE]transformers/dependencies/geometryvalidator8/OGC_SIMPLE_CHECK.fme]FME_CONTROLLER_CHOICE]OGC_SIMPLE_CHECK PLANAR_SURFACE CHECK_AREA]DO_NOT_CHECK_AREA]TOLERANCE_MODE]AUTO]TOLERANCE]<Unused>]ANGULAR_TOLERANCE_MODE]AUTO]ANGULAR_TOLERANCE]<Unused>]FME_CONTROLLER_QUERY_FILE]transformers/dependencies/geometryvalidator8/PLANAR_SURFACE.fme]FME_CONTROLLER_CHOICE]PLANAR_SURFACE SELF_INTERSECTING CHECK_HOLE_TOUCHING_POLYGON]No]CONNECT_Z_MODE_SI]FIRST_WINS]SELF_INTERSECTION_TOLERANCE]None]INTERSECT_ACROSS_MULTIS]No]FME_CONTROLLER_QUERY_FILE]transformers/dependencies/geometryvalidator8/SELF_INTERSECTING.fme]FME_CONTROLLER_CHOICE]SELF_INTERSECTING SHELL_VALIDATION FLIP_APPEARANCE_MODE]FLIP_APPEARANCES]FME_CONTROLLER_QUERY_FILE]transformers/dependencies/geometryvalidator8/SHELL_VALIDATION.fme]FME_CONTROLLER_CHOICE]SHELL_VALIDATION SOLID_VOID_REPAIR FME_CONTROLLER_QUERY_FILE]transformers/dependencies/geometryvalidator8/SOLID_VOID_REPAIR.fme]FME_CONTROLLER_CHOICE]SOLID_VOID_REPAIR TYPE_REPAIR CONNECT_Z_MODE]FIRST_WINS]ARC_ENDPOINT_TOLERANCE_MODE]Auto]ARC_ENDPOINT_TOLERANCE]<Unused>]FME_CONTROLLER_QUERY_FILE]transformers/dependencies/geometryvalidator8/TYPE_REPAIR.fme]FME_CONTROLLER_CHOICE]TYPE_REPAIR MISMATCHED_DIMENSIONS FORCE_DIMENSION]2D]MISMATCHED_Z_VAL]<Unused>]FME_CONTROLLER_QUERY_FILE]transformers/dependencies/geometryvalidator8/MISMATCHED_DIMENSIONS.fme]FME_CONTROLLER_CHOICE]MISMATCHED_DIMENSIONS MISSING_MEASURES_AND_ELEVATIONS MISSING_VALUES_MODE]SENTINEL]MISSING_MEASURES_MODE]<Unused>]SENTINEL_VALUE]0]LENGTH_DIMENSION]<Unused>]FME_CONTROLLER_QUERY_FILE]transformers/dependencies/geometryvalidator8/MISSING_MEASURES_AND_ELEVATIONS.fme]FME_CONTROLLER_CHOICE]MISSING_MEASURES_AND_ELEVATIONS SURFACE_ORIENTATION FME_CONTROLLER_QUERY_FILE]transformers/dependencies/geometryvalidator8/SURFACE_ORIENTATION.fme]FME_CONTROLLER_CHOICE]SURFACE_ORIENTATION SOLID_ORIENTATION FME_CONTROLLER_QUERY_FILE]transformers/dependencies/geometryvalidator8/SOLID_ORIENTATION.fme]FME_CONTROLLER_CHOICE]SOLID_ORIENTATION
    SUMMARY = Detailed
    PASSED -> AttributeManager
    FAILED -> Logger
    REPAIRED -> AttributeManager
AttributeManager
    ATTR_TABLE:
      REMOVE _list{}
      REMOVE Beheerderscode{}
    -> AttributeCreator_35
Logger
    LOG_FEATURE = LOG_RECORD
    MAXCOORDS = 20
    MAXFEATS = 20
    MESSAGE = EV buffer invalid geometry.
    SEVERITY = WARN
Note: Merge beheerder met netwerkcodes
FeatureMerger
    ATTR_ACCUM_MODE = Merge Supplier
    ATTR_CONFLICT_RES_LOOKUP = REQUESTOR_IF_CONFLICT
    GROUP_BY = path_filename
    IGNORE_NULLS = No
    JOIN_KEYS = @Value(BeheerderCode) @Value(BeheerderCode) AUTO
    MERGE_TYPE = Attributes Only
    PRESERVE_FEATURE_ORDER_LOOKUP = PER_OUTPUT_PORT
    PROCESS_DUPS = NO
    REJECT_NULL_MISSING_KEYS = No
    SUPPLIERS_FIRST = No
    ATTR_CONFLICT_RES = Use Requestor
    MERGED -> AttributeRemover_16
    MERGED -> FeatureMerger_3 [SUPPLIER]
    UNMERGED_REQUESTOR -> Logger_2
    UNUSED_SUPPLIER -> Logger_2
Note: Merge individuele K&L met beheerders en netwerkcodes
FeatureMerger_3
    ATTR_ACCUM_MODE = Merge Supplier
    ATTR_CONFLICT_RES_LOOKUP = REQUESTOR_IF_CONFLICT
    GROUP_BY = path_filename
    IGNORE_NULLS = No
    JOIN_KEYS = @Value(NetwerkId) @Value(NetwerkId) AUTO
    MERGE_TYPE = Attributes Only
    PRESERVE_FEATURE_ORDER_LOOKUP = PER_OUTPUT_PORT
    PROCESS_DUPS = NO
    REJECT_NULL_MISSING_KEYS = No
    SUPPLIERS_FIRST = No
    ATTR_CONFLICT_RES = Use Requestor
    MERGED -> FeatureMerger_4 [REQUESTOR]
    UNMERGED_REQUESTOR -> Logger_3
    USED_SUPPLIER -> FeatureMerger_5 [SUPPLIER]
    UNUSED_SUPPLIER -> Logger_3
Note: Individuele K&L mergen met geografisch netwerk
FeatureMerger_4
    ATTR_ACCUM_MODE = Merge Supplier
    ATTR_CONFLICT_RES_LOOKUP = REQUESTOR_IF_CONFLICT
    GROUP_BY = path_filename
    IGNORE_NULLS = No
    JOIN_KEYS = @Value(LinkId) @Value(LijnId) AUTO
    MERGE_TYPE = Attributes and Geometry
    PRESERVE_FEATURE_ORDER_LOOKUP = PER_OUTPUT_PORT
    PROCESS_DUPS = NO
    REJECT_NULL_MISSING_KEYS = No
    SUPPLIERS_FIRST = No
    ATTR_CONFLICT_RES = Use Requestor
    MERGED -> Junction_4
    UNMERGED_REQUESTOR -> FeatureMerger_5 [SUPPLIER]
    UNUSED_SUPPLIER -> AttributeSplitter_14
FeatureMerger_5
    ATTR_ACCUM_MODE = Merge Supplier
    ATTR_CONFLICT_RES_LOOKUP = REQUESTOR_IF_CONFLICT
    GROUP_BY = path_filename
    IGNORE_NULLS = No
    JOIN_KEYS = @Value(BeheerderCode) @Value(BeheerderCode) AUTO
    MERGE_TYPE = Attributes and Geometry
    PRESERVE_FEATURE_ORDER_LOOKUP = PER_OUTPUT_PORT
    PROCESS_DUPS = NO
    REJECT_NULL_MISSING_KEYS = No
    SUPPLIERS_FIRST = No
    ATTR_CONFLICT_RES = Use Requestor
    MERGED -> AttributeRenamer_15
    UNMERGED_REQUESTOR -> AttributeRenamer_15
    UNMERGED_REQUESTOR -> Logger_4
AttributeRenamer_15
    ATTR_TABLE = RENAME_SET_DEFAULT beginLifespanVersion > validFrom
    KEEP_RENAMED_ONLY = no
    MISSING_INPUT_ATTRS = REMOVE
    -> Junction_4
Logger_4
    LOG_FEATURE = LOG_RECORD
    MAXCOORDS = 20
    MAXFEATS = 20
    MESSAGE = Geen match kunnen maken tussen geometrie en attributen. Output word ruw weggeschreven
    SEVERITY = WARN
Logger_3
    LOG_FEATURE = LOG_RECORD
    MAXCOORDS = 20
    MAXFEATS = 20
    MESSAGE = Unmergeds tussen K&L en beheerders met netwerkcodes., mogelijk een brondata fout.
    SEVERITY = WARN
AttributeRemover_16
    REMOVE_ATTRS = path_directory_unix,path_directory_windows,path_extension,path_rootname,path_type,path_unix,path_windows
    -> FeatureMerger_2 [SUPPLIER]
Logger_2
    LOG_FEATURE = LOG_RECORD
    MAXCOORDS = 20
    MAXFEATS = 20
    MESSAGE = Unmergeds tussen Netwerken en Beheerders., mogelijk een brondata fout.
    SEVERITY = WARN
Note: Mergen met beheerders
FeatureMerger_2
    ATTR_ACCUM_MODE = Merge Supplier
    ATTR_CONFLICT_RES_LOOKUP = REQUESTOR_IF_CONFLICT
    GROUP_BY = path_filename
    IGNORE_NULLS = No
    JOIN_KEYS = @Value(NetwerkId) @Value(NetwerkId) AUTO
    MERGE_TYPE = Attributes and Geometry
    PRESERVE_FEATURE_ORDER_LOOKUP = PER_OUTPUT_PORT
    PROCESS_DUPS = NO
    REJECT_NULL_MISSING_KEYS = No
    SUPPLIERS_FIRST = No
    ATTR_CONFLICT_RES = Use Requestor
    MERGED -> Junction_4
    UNMERGED_REQUESTOR -> Junction_4
Junction_4
    -> SchemaSetter [Input_2]
SchemaSetter
    ForceDataType = No
    SORT = None
    Output_2 -> AttributeCreator_30
AttributeRenamer
    ATTR_TABLE = RENAME_SET_DEFAULT ThemaOmschrijving > thema
    KEEP_RENAMED_ONLY = no
    MISSING_INPUT_ATTRS = REMOVE
    -> AttributeRemover_4
AttributeRemover_4
    LIST_ATTRS = _issues{} _issues{}.count _issues{}.issue_found _issues{}.location_sample.x _issues{}.location_sample.y _issues{}.location_sample.z _issues{}.repair_state _listBeheerder{} _listName2{} _listName{} _list{} fme_geometry{}
    REMOVE_ATTRS = Output,_geometry_name,_issues{0}.count,_issues{0}.issue_found,_issues{0}.location_sample.x,_issues{0}.location_sample.y,_issues{0}.location_sample.z,_issues{0}.repair_state,_listBeheerder{0},_listName2{0},_listName{0},_list_index,_list{0},_part_number,fme_geometry{0}
    -> Junction_5
    -> FeatureWriter_2 [Area]
    -> Sampler_2
AttributeSplitter_19
    ATTR_NAME = _dataset
    DELIMITER = Levering_
    DROP_EMPTY_PARTS = No
    LIST_NAME = _list
    TRIM_COMMAND = trim
    TRIM_OPTION = Both
    -> AttributeSplitter_20
AttributeSplitter_20
    ATTR_NAME = _list{1}
    DELIMITER = .gpkg
    DROP_EMPTY_PARTS = No
    LIST_NAME = _list
    TRIM_COMMAND = trim
    TRIM_OPTION = Both
    -> AttributeCreator_37
AttributeCreator_37
    ATTR_TABLE = SET_TO Naam = @Value(_list{0})
    -> Output_location_styled (output)
Output_location_styled (output)
Note: Output
Junction_5
    -> Output_raw (output)
Output_raw (output)

Bookmark: XML pad uit zip lezen
Creation_instance (input)
    -> FeatureReader [INITIATOR]
FeatureReader
    ATTRIBUTES = PATH,"path_unix,path_windows,path_rootname,path_filename,path_extension,path_directory_unix,path_directory_windows,path_type,fme_geometry{0}"
    ATTR_ACCUM_MODE = Only Use Result
    COMBINE_GEOM = Use Result
    DATASET = $(KLIC_FOLDER)
    FORMAT = PATH
    OUTPUT_FEATURES_DISPLAY = Schema and Data Features
    PATH_GLOB_PATTERN = *
    PATH_NO_EMPTY_PROPERTIES = YES
    PATH_OFFSET_DATETIME = yes
    PATH_RECURSE_DIRECTORIES = NO
    PATH_RETRIEVE_FILE_PROPERTIES = NO
    PATH_TYPE = ANY
    PATH_USE_NON_STRING_ATTR = yes
    PATH -> Tester
Tester
    BOOL_OP = AND
    TEST_CLAUSE:
      TEST @Value(path_extension) = zip
      CASE_INSENSITIVE_TEST @Value(path_rootname) BEGINS_WITH Levering_
    TEST_MODE = TEST
    PASSED -> StringReplacer_53
    FAILED -> Tester_2
AttributeExposer_2
    ATTR_LIST = path_directory_unix,path_directory_windows,path_extension,path_filename,path_geom,path_rootname,path_type,path_unix,path_windows
    -> AttributeSplitter_4
StringReplacer_53
    CASE = NO
    FIND_TEXT = Levering_
    NO_MATCH = _FME_NO_OP_
    REGEXP = NO
    SRC_ATTRS = path_rootname
    -> AttributeSplitter
AttributeSplitter
    ATTR_NAME = path_rootname
    DELIMITER = _
    DROP_EMPTY_PARTS = No
    LIST_NAME = _list
    TRIM_COMMAND = trim
    TRIM_OPTION = Both
    -> AttributeCreator
AttributeSplitter_4
    ATTR_NAME = path_windows
    DELIMITER = \
    DROP_EMPTY_PARTS = No
    LIST_NAME = _list
    TRIM_COMMAND = trim
    TRIM_OPTION = Both
    -> ListSearcher
ListSearcher
    ATTR_VALUE = ^GI_gebiedsinformatielevering
    CASE = CASE_SENSITIVE
    INDEX_ATTR = _list_index
    LIST_ATTR = _list{}
    MATCHTYPE = REGULAR_EXPRESSION_ENCODED
    PRESERVE_FEATURE_ORDER_LOOKUP = PER_OUTPUT_PORT
    FOUND -> Tester_5
Tester_5
    BOOL_OP = OR
    TEST_CLAUSE = TEST @Value(path_extension) = xml
    TEST_MODE = TEST
    PASSED -> DuplicateFilter_2
DuplicateFilter_2
    INPUT_ORDERED_CHOICE_LOOKUP = NO
    KEYATTR = path_filename
    PRESERVE_FEATURE_ORDER_LOOKUP = PER_OUTPUT_PORT
    INPUT_ORDERED_CHOICE = No
    UNIQUE -> FeatureReader_6 [INITIATOR]
Note: Altijd generic in laten lezen
FeatureReader_6
    ATTRS_TO_EXPOSE = fme_feature_type
    ATTR_ACCUM_MODE = Merge Initiator and Result
    ATTR_CONFLICT_RES = Use Result
    ATTR_IGNORE_NULLS = No
    COMBINE_GEOM = Use Result
    DATASET = @Value(path_windows)
    FORMAT = GML
    GML_ADD_GEOMETRIES_AS_XML_FRAGMENTS = NO
    GML_CACHE_XSD = yes
    GML_CONTINUE_ON_GEOM_ERROR = yes
    GML_DISABLE_AUTOMATIC_READER_TYPE_SELECTION = NO
    GML_DISABLE_XML_NAMESPACE_PROCESSING = NO
    GML_ENFORCE_PATH_CONTINUITY_BY = SNAPPING_END_POINTS
    GML_EXPLORE_XSD_VALUES = NO
    GML_FEATURE_TYPES_SCHEMA_MODE = XML_SCHEMA
    GML_FLATTEN_XML_FRAGMENTS = NO
    GML_IGNORE_APPLICATON_SCHEMA = no
    GML_MAP_ALL_SUBSTITUTABLE_PROPERTIES = YES
    GML_MAP_COMPLEX_PROPERTIES_AS = Nested Attributes
    GML_MAP_COVERAGES_AS_FEATURE_TYPES = NO
    GML_MAP_EMBEDDED_OBJECTS_AS = ATTRIBUTES
    GML_MAP_GEOMETRY_COLUMNS = YES
    GML_MAP_PREDEFINED_GML_PROPERTIES = NO
    GML_MULTI_VALUE_SIMPLE_PROPERTIES_AS_CSV = no
    GML_PROCESS_XLINK_GEOMETRIES = No
    GML_REPROJECT_DISPARATE_CRS_IN_MULTIPLE_GEOMETRIES = yes
    GML_SKIP_SCHEMA_LOCATION_IN_DATASET = No
    GML_SUPPORTED_READER_ARCHIVE_EXTENSIONS = xml.gz,gml.gz
    GML_USE_OLD_READER = NO
    GML_USE_SEARCH_ENVELOPE = NO
    GML_VALIDATE_DATASET = no
    GML_XML_FRAGMENTS_AS_DOCUMENTS = YES
    INTERACT = NONE
    OUTPUT_FEATURES_DISPLAY = Schema and Data Features
    <OTHER> -> AttributeFilter

Bookmark: Already unzipped
Tester_2
    BOOL_OP = COMPOSITE
    COMPOSITE_TEST = 1 AND 2
    TEST_CLAUSE:
      CASE_INSENSITIVE_TEST @Value(path_rootname) BEGINS_WITH Levering_
      CASE_INSENSITIVE_TEST @Value(path_type) = directory
    TEST_MODE = CASE_INSENSITIVE_TEST
    PASSED -> FeatureReader_3 [INITIATOR]
    FAILED -> Tester_3
Tester_3
    BOOL_OP = OR
    TEST_CLAUSE = CASE_INSENSITIVE_TEST @Value(path_type) = directory
    TEST_MODE = CASE_INSENSITIVE_TEST
    PASSED -> FeatureReader_2 [INITIATOR]
FeatureReader_2
    ATTR_ACCUM_MODE = Only Use Result
    COMBINE_GEOM = Use Result
    DATASET = @Value(path_windows)
    FORMAT = PATH
    OUTPUT_FEATURES_DISPLAY = Schema and Data Features
    PATH_GLOB_PATTERN = *
    PATH_NO_EMPTY_PROPERTIES = YES
    PATH_OFFSET_DATETIME = yes
    PATH_RECURSE_DIRECTORIES = YES
    PATH_RETRIEVE_FILE_PROPERTIES = NO
    PATH_TYPE = ANY
    PATH_USE_NON_STRING_ATTR = yes
    <OTHER> -> AttributeExposer
AttributeExposer
    ATTR_LIST = path_filename,path_directory_unix,path_directory_windows,path_extension,path_geom,path_rootname,path_type,path_unix,path_windows
    -> Tester_4
Tester_4
    BOOL_OP = COMPOSITE
    COMPOSITE_TEST = 1 AND 2
    TEST_CLAUSE:
      CASE_INSENSITIVE_TEST @Value(path_rootname) BEGINS_WITH Levering_
      CASE_INSENSITIVE_TEST @Value(path_type) = directory
    TEST_MODE = CASE_INSENSITIVE_TEST
    PASSED -> StringReplacer_52
StringReplacer_52
    CASE = NO
    FIND_TEXT = Levering_
    NO_MATCH = _FME_NO_OP_
    REGEXP = NO
    SRC_ATTRS = path_rootname
    -> AttributeSplitter_2
AttributeSplitter_2
    ATTR_NAME = path_rootname
    DELIMITER = _
    DROP_EMPTY_PARTS = No
    LIST_NAME = _list
    TRIM_COMMAND = trim
    TRIM_OPTION = Both
    -> AttributeCreator_2
AttributeCreator_2
    ATTR_TABLE = SET_TO Naam (varchar(200)) = @Value(_list{0})
    -> DuplicateFilter
    -> ChangeDetector_2 [REVISED]
DuplicateFilter
    INPUT_ORDERED_CHOICE_LOOKUP = NO
    KEYATTR = path_filename
    PRESERVE_FEATURE_ORDER_LOOKUP = PER_OUTPUT_PORT
    INPUT_ORDERED_CHOICE = No
    UNIQUE -> FeatureReader_4 [INITIATOR]
Note: Duplicate check voor wanneer gebruiker 2x heeft uitgepakt,
FeatureReader_4
    ATTR_ACCUM_MODE = Only Use Result
    COMBINE_GEOM = Use Result
    DATASET = @Value(path_windows)
    FORMAT = PATH
    OUTPUT_FEATURES_DISPLAY = Schema and Data Features
    PATH_GLOB_PATTERN = *
    PATH_NO_EMPTY_PROPERTIES = YES
    PATH_OFFSET_DATETIME = yes
    PATH_RECURSE_DIRECTORIES = YES
    PATH_RETRIEVE_FILE_PROPERTIES = NO
    PATH_TYPE = ANY
    PATH_USE_NON_STRING_ATTR = yes
    <OTHER> -> AttributeExposer_2
FeatureReader_3
    ATTR_ACCUM_MODE = Only Use Result
    COMBINE_GEOM = Use Result
    DATASET = $(KLIC_FOLDER)\unzippedKLIC
    FORMAT = PATH
    OUTPUT_FEATURES_DISPLAY = Schema and Data Features
    PATH_GLOB_PATTERN = *
    PATH_NO_EMPTY_PROPERTIES = YES
    PATH_OFFSET_DATETIME = yes
    PATH_RECURSE_DIRECTORIES = NO
    PATH_RETRIEVE_FILE_PROPERTIES = NO
    PATH_TYPE = ANY
    PATH_USE_NON_STRING_ATTR = yes
    <OTHER> -> AttributeSplitter_4

Bookmark: Unzip
AttributeCreator
    ATTR_TABLE = SET_TO Naam = @Value(_list{0})
    -> ChangeDetector_2 [ORIGINAL]
ChangeDetector_2
    BLANK_AND_MISSING_DIFFER = No
    CHECK_TYPES_AND_ENCODINGS = No
    CNT_ATTR = _match_id
    MATCHATTRS = Naam
    MATCH_STRATEGY_LOOKUP = MATCH
    UNCHANGED_OUTPUT = Output Both
    UPSERT_MODE = No
    MATCH_STRATEGY = Match Selected Attributes
    DELETED -> ZipExtractor
Note: Indien je een error krijgt zoals "no such path found" of "unexepcted error" dan kan het er aan liggen dat je de max van 255 karakters hebt bereikt. Kies een andere locatie
ZipExtractor
    PRESERVE = No
    RECURSIVE = No
    REPLACE = No
    ROOT_FOLDER = $(KLIC_FOLDER)/unzippedKLIC
    ZIP_PATH = @Value(path_windows)
    File -> DuplicateFilter_3
    <Rejected> -> Logger_5
DuplicateFilter_3
    INPUT_ORDERED_CHOICE_LOOKUP = NO
    KEYATTR = Naam
    PRESERVE_FEATURE_ORDER_LOOKUP = PER_OUTPUT_PORT
    INPUT_ORDERED_CHOICE = No
    UNIQUE -> AttributeSplitter_3
AttributeSplitter_3
    ATTR_NAME = path_windows
    DELIMITER = unzippedKLIC
    DROP_EMPTY_PARTS = No
    LIST_NAME = _path
    TRIM_COMMAND = trim
    TRIM_OPTION = Both
    -> AttributeCreator_38
AttributeCreator_38
    ATTR_TABLE = SET_TO path = @Value(_path{0})\unzippedKLIC
    -> FeatureReader_5 [INITIATOR]
FeatureReader_5
    ATTR_ACCUM_MODE = Only Use Result
    COMBINE_GEOM = Use Result
    DATASET = @Value(path)
    FORMAT = PATH
    OUTPUT_FEATURES_DISPLAY = Schema and Data Features
    PATH_GLOB_PATTERN = *
    PATH_NO_EMPTY_PROPERTIES = YES
    PATH_OFFSET_DATETIME = yes
    PATH_RECURSE_DIRECTORIES = YES
    PATH_RETRIEVE_FILE_PROPERTIES = NO
    PATH_TYPE = ANY
    PATH_USE_NON_STRING_ATTR = yes
    <OTHER> -> AttributeExposer_3
AttributeExposer_3
    ATTR_LIST = path_directory_unix,path_directory_windows,path_extension,path_filename,path_geom,path_rootname,path_type,path_unix,path_windows
    -> AttributeSplitter_4
Logger_5
    LOG_FEATURE = LOG_RECORD
    MAXCOORDS = 20
    MAXFEATS = 20
    MESSAGE = Could not unzip KLIC
    SEVERITY = WARN

Bookmark: XML uitlezen per onderdeel
AttributeFilter
    ATTR_NAME = fme_feature_type
    ATTR_VALUES = <Empty>,<Missing>,<Null>,<Unfiltered>,AanduidingEisVoorzorgsmaatregel,UtilityLink,Waterleiding,Elektriciteitskabel,Overig,Rioolleiding,OlieGasChemicalienPijpleiding,Telecommunicatiekabel,ThermischePijpleiding,Kabelbed,Mantelbuis,Duct,Utiliteitsnet,Beheerder,Appurtenance,Maatvoering,ExtraGeometrie,TechnischGebouw,Mangat,Kast,ExtraDetailinfo,EigenTopografie,DiepteTovMaaiveld,Annotatie,DiepteNAP,Mast,Toren
    PRESERVE_FEATURE_ORDER_LOOKUP = PER_OUTPUT_PORT
    <UNFILTERED> -> Junction
    AanduidingEisVoorzorgsmaatregel -> AttributeExposer_4
    UtilityLink -> AttributeCreator_4
    Waterleiding -> Junction_2
    Elektriciteitskabel -> Junction_2
    Overig -> Junction_2
    Rioolleiding -> Junction_2
    OlieGasChemicalienPijpleiding -> Junction_2
    Telecommunicatiekabel -> Junction_2
    ThermischePijpleiding -> Junction_2
    Kabelbed -> Junction_2
    Mantelbuis -> Junction_2
    Duct -> Junction_2
    Utiliteitsnet -> AttributeExposer_7
    Beheerder -> AttributeExposer_8
    Appurtenance -> AttributeExposer_21
    Maatvoering -> AttributeExposer_19
    ExtraGeometrie -> AttributeExposer_20
    TechnischGebouw -> AttributeExposer_12
    Mangat -> AttributeExposer_13
    Kast -> AttributeExposer_14
    ExtraDetailinfo -> AttributeExposer_15
    EigenTopografie -> AttributeExposer_16
    DiepteTovMaaiveld -> AttributeExposer_17
    Annotatie -> AttributeExposer_18
    DiepteNAP -> AttributeExposer_10
    Mast -> AttributeExposer_11
    Toren -> AttributeExposer_9

Bookmark: EisVoorzorgsmaatregel
AttributeExposer_4
    ATTR_LIST = contactVoorzorgsmaatregel.Contact.email,contactVoorzorgsmaatregel.Contact.naam,contactVoorzorgsmaatregel.Contact.telefoon,eisVoorzorgsmaatregel,gml_id,netbeheerderNetAanduiding,netbeheerderNetOmschrijving
    -> AttributeSplitter_5
AttributeSplitter_5
    ATTR_NAME = gml_id
    DELIMITER = nl.imkl-
    DROP_EMPTY_PARTS = No
    LIST_NAME = Beheerderscode
    TRIM_COMMAND = trim
    TRIM_OPTION = Both
    -> AttributeSplitter_6
AttributeSplitter_6
    ATTR_NAME = Beheerderscode{1}
    DELIMITER = .
    DROP_EMPTY_PARTS = No
    LIST_NAME = Beheerderscode
    TRIM_COMMAND = trim
    TRIM_OPTION = Both
    -> AttributeCreator_5
AttributeCreator_5
    ATTR_TABLE = SET_TO BeheerderCode = @Value(Beheerderscode{0})
    -> AttributeSplitter_7
AttributeSplitter_7
    ATTR_NAME = gml_id
    DELIMITER = EisVoorzorgsmaatregel__
    DROP_EMPTY_PARTS = No
    LIST_NAME = _list
    TRIM_COMMAND = trim
    TRIM_OPTION = Both
    -> AttributeSplitter_8
AttributeSplitter_8
    ATTR_NAME = _list{1}
    DELIMITER = __
    DROP_EMPTY_PARTS = No
    LIST_NAME = _list
    TRIM_COMMAND = trim
    TRIM_OPTION = Both
    -> AttributeCreator_6
AttributeCreator_6
    ATTR_TABLE = SET_TO Type (varchar(200)) = @Value(_list{0})
    -> Dissolver
Dissolver
    ACCUM_INPUT_ATTRS = Merge Incoming Attributes
    CLEANING_TOLERANCE_LOOKUP = AUTO
    CONNECT_Z_MODE_LOOKUP = FIRST_WINS
    DEAGGREGATE_INPUT = Yes
    GROUP_BY = eisVoorzorgsmaatregel
    CLEANING_TOLERANCE = Automatic
    CONNECT_Z_MODE = First Wins
    AREA -> FeatureMerger_7 [REQUESTOR]

Bookmark: UtilityLink geometrieën
AttributeCreator_4
    ATTR_TABLE:
      SET_TO inspireId.Identifier.localId = @CurrentAttribute()
      SET_TO LijnId = @Value(inspireId.Identifier.localId)
    -> AttributeKeeper_3
AttributeKeeper_3
    CREATE_BULK_MODE_FEATURES = NO
    KEEP_ATTRS = path_filename,LijnId
    -> FeatureMerger_4 [SUPPLIER]

Bookmark: K&L informatie exposen en creatie
StringReplacer_6
    CASE = NO
    FIND_TEXT = http://inspire.ec.europa.eu/codelist/ConditionOfFacilityValue/
    NO_MATCH = _FME_NO_OP_
    REGEXP = NO
    SRC_ATTRS = currentStatus.xlink_href
    -> StringReplacer_7
StringReplacer_7
    CASE = NO
    FIND_TEXT = http://inspire.ec.europa.eu/codelist/WarningTypeValue/
    NO_MATCH = _FME_NO_OP_
    REGEXP = NO
    SRC_ATTRS = warningType.xlink_href
    -> AttributeCreator_7
AttributeCreator_7
    ATTR_TABLE:
      SET_TO nominalVoltage (V) = FME_CONDITIONAL:DEFAULT_VALUE'ERROR'BOOL_OP;OR;COMPOSITE_TEST;1;TEST @Value(nominalVoltage.uom) = urn:ogc:def:uom:OGC::V'@Value(nominalVoltage)'BOOL_OP;OR;COMPOSITE_TEST;1;TEST nominalVoltage.uom ATTRIBUTE_IS_MISSING _FME_BLANK_STRING_'_FME_NO_OP_'FME_NUM_CONDITIONS3___
      SET_TO operatingVoltage (V) = FME_CONDITIONAL:DEFAULT_VALUE'ERROR'BOOL_OP;OR;COMPOSITE_TEST;1;TEST @Value(operatingVoltage.uom) = urn:ogc:def:uom:OGC::V'@Value(operatingVoltage)'BOOL_OP;OR;COMPOSITE_TEST;1;TEST operatingVoltage.uom ATTRIBUTE_IS_MISSING _FME_BLANK_STRING_'_FME_NO_OP_'FME_NUM_CONDITIONS3___
      SET_TO pipeDiameter (mm) = FME_CONDITIONAL:DEFAULT_VALUE'ERROR'BOOL_OP;OR;COMPOSITE_TEST;1;TEST @Value(pipeDiameter.uom) = urn:ogc:def:uom:OGC::mm'_FME_NO_OP_'BOOL_OP;OR;COMPOSITE_TEST;1;TEST @Value(pipeDiameter.uom) = urn:ogc:def:uom:OGC::cm'@Evaluate(@Value(pipeDiameter)*10)'BOOL_OP;OR;COMPOSITE_TEST;1;TEST @Value(pipeDiameter.uom) = urn:ogc:def:uom:OGC::m'@Evaluate(@Value(pipeDiameter)*100)'BOOL_OP;OR;COMPOSITE_TEST;1;TEST pipeDiameter.uom ATTRIBUTE_IS_MISSING _FME_BLANK_STRING_'_FME_NO_OP_'FME_NUM_CONDITIONS5___
      SET_TO pressure (bar) = FME_CONDITIONAL:DEFAULT_VALUE'ERROR'BOOL_OP;OR;COMPOSITE_TEST;1;TEST @Value(pressure.uom) = urn:ogc:def:uom:OGC::bar'@Value(pressure)'BOOL_OP;OR;COMPOSITE_TEST;1;TEST pressure.uom ATTRIBUTE_IS_MISSING _FME_BLANK_STRING_'_FME_NO_OP_'FME_NUM_CONDITIONS3___
      SET_TO warningType = @Value(warningType.xlink_href)
      SET_TO status = @Value(currentStatus.xlink_href)
    -> Tester_6
    -> AttributeRemover_2
AttributeRemover_2
    REMOVE_ATTRS = nominalVoltage,nominalVoltage.uom,operatingVoltage,operatingVoltage.uom,pipeDiameter,pipeDiameter.uom,pressure,pressure.uom
    -> ListElementCounter
ListElementCounter
    CNT_ATTR = link_element_count
    LIST_NAME = link{}
    -> AttributeCreator_8
AttributeCreator_8
    ATTR_TABLE:
      SET_TO count (real64) = @Evaluate(@Value(link_element_count)-1
        )
    -> AttributeCreator_9
AttributeCreator_9
    ATTR_TABLE = SET_TO LinkId (varchar(200)) = @Value(link{@Value(count)}.xlink_href)
    -> AttributeExposer_6
AttributeExposer_6
    ATTR_LIST = inNetwork{0}.xlink_href,buismateriaalType.xlink_href,telecommunicationsCableMaterialType.xlink_href
    -> AttributeCreator_10
AttributeCreator_10
    ATTR_TABLE = SET_TO NetwerkId = @Value(inNetwork{0}.xlink_href)
    -> StringReplacer
StringReplacer
    CASE = NO
    FIND_TEXT = @Value(inspireId.Identifier.namespace)-
    NO_MATCH = _FME_NO_OP_
    REGEXP = NO
    SRC_ATTRS = NetwerkId,LinkId
    -> AttributeCreator_11
AttributeCreator_11
    ATTR_TABLE = SET_TO MaterialType = FME_CONDITIONAL:DEFAULT_VALUE'_FME_NO_OP_'BOOL_OP;OR;COMPOSITE_TEST;1;TEST telecommunicationsCableMaterialType.xlink_href ATTRIBUTE_HAS_A_VALUE _FME_BLANK_STRING_'@Value(telecommunicationsCableMaterialType.xlink_href)'BOOL_OP;OR;COMPOSITE_TEST;1;TEST buismateriaalType.xlink_href ATTRIBUTE_HAS_A_VALUE _FME_BLANK_STRING_'@Value(buismateriaalType.xlink_href)'FME_NUM_CONDITIONS3___
    -> AttributeSplitter_9
AttributeSplitter_9
    ATTR_NAME = MaterialType
    DELIMITER = /TelecommunicationsCableMaterialTypeIMKLValue/
    DROP_EMPTY_PARTS = No
    LIST_NAME = MateriaalType_Telco
    TRIM_COMMAND = trim
    TRIM_OPTION = Both
    -> AttributeSplitter_10
AttributeSplitter_10
    ATTR_NAME = MaterialType
    DELIMITER = PipeMaterialTypeIMKLValue/
    DROP_EMPTY_PARTS = No
    LIST_NAME = MateriaalType_Buis
    TRIM_COMMAND = trim
    TRIM_OPTION = Both
    -> AttributeCreator_12
AttributeCreator_12
    ATTR_TABLE = SET_TO MaterialType = FME_CONDITIONAL:DEFAULT_VALUE'_FME_NO_OP_'BOOL_OP;AND;COMPOSITE_TEST;1 AND 2;TEST MateriaalType_Telco{1} ATTRIBUTE_HAS_A_VALUE _FME_BLANK_STRING_;TEST @Value(MateriaalType_Telco{1}) != onbekend'@Value(MateriaalType_Telco{1})'BOOL_OP;AND;COMPOSITE_TEST;1 AND 2;CASE_INSENSITIVE_TEST @Value(MateriaalType_Telco{1}) = onbekend;CASE_INSENSITIVE_TEST @Value(LinkId) CONTAINS Copper'copper_cable'BOOL_OP;AND;COMPOSITE_TEST;1 AND 2;CASE_INSENSITIVE_TEST @Value(MateriaalType_Telco{1}) = onbekend;CASE_INSENSITIVE_TEST @Value(LinkId) CONTAINS fiber'optical fiber'BOOL_OP;AND;COMPOSITE_TEST;1 AND 2;CASE_INSENSITIVE_TEST @Value(MateriaalType_Telco{1}) = onbekend;CASE_INSENSITIVE_TEST @Value(LinkId) CONTAINS twisted'twisted pair'BOOL_OP;AND;COMPOSITE_TEST;1 AND 2;TEST MateriaalType_Buis{1} ATTRIBUTE_HAS_A_VALUE _FME_BLANK_STRING_;TEST @Value(MateriaalType_Buis{1}) != onbekend'@Value(MateriaalType_Buis{1})'BOOL_OP;OR;COMPOSITE_TEST;1;TEST MaterialType ATTRIBUTE_IS_MISSING _FME_BLANK_STRING_''FME_NUM_CONDITIONS7___
    -> AttributeRemover_6
AttributeRemover_6
    LIST_ATTRS = MateriaalType_Buis{} MateriaalType_Telco{} _list{} inNetwork{} inNetwork{}.xlink_href link{} link{}.xlink_href
    REMOVE_ATTRS = MateriaalType_Buis{0},MateriaalType_Telco{0},_list{0},buismateriaalType.xlink_href,currentStatus.xlink_href,inNetwork{0}.xlink_href,inspireId.Identifier.namespace,link{0}.xlink_href,path_directory_unix,path_directory_windows,path_extension,path_rootname,path_type,path_unix,path_windows,telecommunicationsCableMaterialType.xlink_href,warningType.xlink_href,count,link_element_count
    -> AttributeRenamer_12
AttributeRenamer_12
    ATTR_TABLE = RENAME_SET_DEFAULT beginLifespanVersion > registratiedatum
    KEEP_RENAMED_ONLY = no
    MISSING_INPUT_ATTRS = REMOVE
    -> FeatureMerger_3 [REQUESTOR]

Bookmark: Tester op incorrecte inputs
Tester_6
    BOOL_OP = OR
    TEST_CLAUSE:
      TEST @Value(nominalVoltage (V)) = ERROR
      TEST @Value(operatingVoltage (V)) = ERROR
      TEST @Value(pipeDiameter (mm)) = ERROR
      TEST @Value(pressure (bar)) = ERROR
    TEST_MODE = TEST
    PASSED -> Terminator_3
Terminator_3
    MESSAGE = Translation Terminated

Bookmark: Netwerken
AttributeExposer_7
    ATTR_LIST = identificatie.NEN3610ID.lokaalID,thema.xlink_href,beginLifespanVersion
    -> AttributeSplitter_11
AttributeSplitter_11
    ATTR_NAME = identificatie.NEN3610ID.lokaalID
    DELIMITER = .
    DROP_EMPTY_PARTS = No
    LIST_NAME = identificatie.NEN3610ID.lokaalID_list
    TRIM_COMMAND = trim
    TRIM_OPTION = Both
    -> AttributeCreator_13
AttributeCreator_13
    ATTR_TABLE:
      SET_TO BeheerderCode = @Value(identificatie.NEN3610ID.lokaalID_list{0})
      SET_TO NetwerkId = @Value(identificatie.NEN3610ID.lokaalID)
    -> AttributeSplitter_12
AttributeSplitter_12
    ATTR_NAME = thema.xlink_href
    DELIMITER = id/waarde/Thema/
    DROP_EMPTY_PARTS = No
    LIST_NAME = _listThema
    TRIM_COMMAND = trim
    TRIM_OPTION = Both
    -> AttributeCreator_14
AttributeCreator_14
    ATTR_TABLE = SET_TO ThemaOmschrijving = @Value(_listThema{1})
    -> AttributeRemover
AttributeRemover
    LIST_ATTRS = _listThema{} identificatie.NEN3610ID.lokaalID_list{} _list{} fme_geometry{}
    REMOVE_ATTRS = _listThema{0},fme_feature_type,identificatie.NEN3610ID.lokaalID,identificatie.NEN3610ID.lokaalID_list{0},thema.xlink_href,beginLifespanVersion,path_directory_unix,path_directory_windows,path_extension,path_rootname,path_type,path_unix,path_windows
    -> FeatureMerger [REQUESTOR]

Bookmark: Alle overige unfilterd thema's
Junction
    -> AttributeCreator_32
AttributeCreator_32
    ATTR_TABLE:
      SET_TO thema = Unprocessed
      SET_TO fme_feature_type = Unprocessed
    -> AttributeCreator_33
AttributeCreator_33
    ATTR_TABLE = SET_TO count = 1
    -> FeatureMerger_6 [REQUESTOR]
Sampler_2
    MODE = ORIGINAL
    RATE = 1
    SAMPLE_TYPE_MULTIPLIER = -1
    SAMPLE_MODE = No
    SAMPLE_TYPE_LONG = First N Features
    SAMPLED -> AttributeKeeper_4
AttributeKeeper_4
    CREATE_BULK_MODE_FEATURES = NO
    KEEP_ATTRS = Klic
    -> AttributeCreator_34
AttributeCreator_34
    ATTR_TABLE = SET_TO count = 1
    -> FeatureMerger_6 [SUPPLIER]
FeatureMerger_6
    ATTR_ACCUM_MODE = Merge Supplier
    ATTR_CONFLICT_RES_LOOKUP = REQUESTOR_IF_CONFLICT
    GROUP_BY = path_filename
    IGNORE_NULLS = No
    JOIN_KEYS = @Value(count) @Value(count) AUTO
    MERGE_TYPE = Attributes Only
    PRESERVE_FEATURE_ORDER_LOOKUP = PER_OUTPUT_PORT
    PROCESS_DUPS = NO
    REJECT_NULL_MISSING_KEYS = No
    SUPPLIERS_FIRST = No
    ATTR_CONFLICT_RES = Use Requestor
    MERGED -> AttributeRemover_20
AttributeRemover_20
    REMOVE_ATTRS = count
    -> FeatureWriter_2 [Area]
    -> Junction_5

Bookmark: Beheerders
AttributeExposer_8
    ATTR_LIST = identificatie.NEN3610ID.lokaalID,organisatie.Organisatie.naam{0}
    -> AttributeSplitter_13
AttributeSplitter_13
    ATTR_NAME = identificatie.NEN3610ID.lokaalID
    DELIMITER = .
    DROP_EMPTY_PARTS = No
    LIST_NAME = identificatie.NEN3610ID.lokaalID_list
    TRIM_COMMAND = trim
    TRIM_OPTION = Both
    -> AttributeCreator_15
AttributeCreator_15
    ATTR_TABLE:
      SET_TO BeheerderCode = @Value(identificatie.NEN3610ID.lokaalID_list{0})
      SET_TO BeheerderOmschrijving = @Value(organisatie.Organisatie.naam{0})
    -> AttributeKeeper
AttributeKeeper
    CREATE_BULK_MODE_FEATURES = NO
    KEEP_ATTRS = BeheerderCode,BeheerderOmschrijving,path_filename
    -> FeatureMerger [SUPPLIER]
    -> FeatureMerger_7 [SUPPLIER]

Bookmark: Automatische output benaming
AttributeCreator_35
    ATTR_TABLE = SET_TO Output = $(FME_MF_DIR_USERTYPED)
    -> StringReplacer_2
StringReplacer_2
    CASE = NO
    FIND_TEXT = /
    NO_MATCH = _FME_NO_OP_
    REGEXP = NO
    REPLACE_TEXT = \
    SRC_ATTRS = Output
    -> AttributeSplitter_17
AttributeSplitter_17
    ATTR_NAME = path_filename
    DELIMITER = GI_gebiedsinformatielevering_
    DROP_EMPTY_PARTS = No
    LIST_NAME = _listName
    TRIM_COMMAND = trim
    TRIM_OPTION = Both
    -> AttributeSplitter_18
AttributeSplitter_18
    ATTR_NAME = _listName{1}
    DELIMITER = .xml
    DROP_EMPTY_PARTS = No
    LIST_NAME = _listName2
    TRIM_COMMAND = trim
    TRIM_OPTION = Both
    -> AttributeCreator_36
AttributeCreator_36
    ATTR_TABLE:
      SET_TO Output = @Value(Output)@Value(_listName2{0}).gpkg
      SET_TO Klic = Levering_@Value(_listName2{0})
    -> AttributeRemover_3
AttributeRemover_3
    LIST_ATTRS = _issues{} _issues{}.count _issues{}.issue_found _issues{}.location_sample.x _issues{}.location_sample.y _issues{}.location_sample.z _listName2{} _listName{} fme_geometry{}
    REMOVE_ATTRS = Output,_listName2{0},_listName{0},_list_index,path_directory_unix,path_directory_windows,path_extension,path_filename,path_rootname,path_type,path_unix,path_windows
    -> FeatureWriter_2 [Area]
    -> Junction_5

Bookmark: Indien geen match word er op bronhoudercode nog een match getracht te maken.
AttributeSplitter_14
    ATTR_NAME = LijnId
    DELIMITER = .
    DROP_EMPTY_PARTS = No
    LIST_NAME = _listBeheerder
    TRIM_COMMAND = trim
    TRIM_OPTION = Both
    -> AttributeCreator_29
AttributeCreator_29
    ATTR_TABLE = SET_TO BeheerderCode = @Value(_listBeheerder{0})
    -> FeatureMerger_5 [REQUESTOR]

Bookmark: Punt geometrieën, extra geometrieën en annotaties
AttributeExposer_9
    ATTR_LIST = inNetwork{0}.xlink_href,currentStatus.xlink_href,validFrom,verticalPosition,inspireId.Identifier.localId,extraGeometrie.xlink_href,label,bovengrondsZichtbaar,geoNauwkeurigheidXY,BGT_ID,rotatiehoekSymbool,inNetwork,dieptelegging
    -> StringReplacer_40
StringReplacer_40
    CASE = NO
    FIND_TEXT = http://inspire.ec.europa.eu/codelist/ConditionOfFacilityValue/
    NO_MATCH = _FME_NO_OP_
    REGEXP = NO
    SRC_ATTRS = currentStatus.xlink_href
    -> ListElementCounter_13
ListElementCounter_13
    CNT_ATTR = link_element_count
    LIST_NAME = inNetwork{}
    -> AttributeCreator_16
AttributeCreator_16
    ATTR_TABLE:
      SET_TO count = @Evaluate(@Value(link_element_count)-1)
      SET_TO LinkId = @Value(inspireId.Identifier.localId)@Value(count)
      SET_TO NetwerkId = @Value(inNetwork{0}.xlink_href)
    -> StringReplacer_39
StringReplacer_39
    CASE = NO
    FIND_TEXT = nl.imkl-
    NO_MATCH = _FME_NO_OP_
    REGEXP = NO
    SRC_ATTRS = NetwerkId,LinkId
    -> AttributeRemover_19
AttributeRemover_19
    LIST_ATTRS = _list{} fme_geometry{} inNetwork{} inNetwork{}.xlink_href
    REMOVE_ATTRS = _list_index,_list{0},fme_geometry{0},inNetwork{0}.xlink_href,inspireId.Identifier.localId,path_directory_unix,path_directory_windows,path_extension,path_rootname,path_type,path_unix,path_windows,telecommunicationsCableMaterialType.xlink_href,buismateriaalType.xlink_href,count,link_element_count
    -> AttributeRenamer_17
AttributeRenamer_17
    ATTR_TABLE:
      RENAME_SET_DEFAULT currentStatus.xlink_href > status
      RENAME_SET_DEFAULT extraGeometrie.xlink_href > geometrie_id
    KEEP_RENAMED_ONLY = no
    MISSING_INPUT_ATTRS = REMOVE
    -> Junction_3
AttributeExposer_10
    ATTR_LIST = inNetwork{0}.xlink_href,diepteAangrijpingspunt.xlink_href,diepteNauwkeurigheid.xlink_href,dieptePeil,identificatie.NEN3610ID.lokaalID,rotatiehoekSymbool
    -> StringReplacer_38
StringReplacer_38
    CASE = NO
    FIND_TEXT = http://definities.geostandaarden.nl/imkl2015/id/waarde/DiepteAangrijpingspuntValue/
    NO_MATCH = _FME_NO_OP_
    REGEXP = NO
    SRC_ATTRS = diepteAangrijpingspunt.xlink_href
    -> StringReplacer_41
StringReplacer_41
    CASE = NO
    FIND_TEXT = http://definities.geostandaarden.nl/imkl2015/id/waarde/NauwkeurigheidDiepteValue/
    NO_MATCH = _FME_NO_OP_
    REGEXP = NO
    SRC_ATTRS = diepteNauwkeurigheid.xlink_href
    -> ListElementCounter_12
ListElementCounter_12
    CNT_ATTR = link_element_count
    LIST_NAME = inNetwork{}
    -> AttributeCreator_17
AttributeCreator_17
    ATTR_TABLE:
      SET_TO count = @Evaluate(@Value(link_element_count)-1)
      SET_TO LinkId = @Value(identificatie.NEN3610ID.lokaalID)@Value(count)
      SET_TO NetwerkId = @Value(inNetwork{0}.xlink_href)
    -> StringReplacer_37
StringReplacer_37
    CASE = NO
    FIND_TEXT = nl.imkl-
    NO_MATCH = _FME_NO_OP_
    REGEXP = NO
    SRC_ATTRS = NetwerkId,LinkId
    -> AttributeRemover_18
AttributeRemover_18
    LIST_ATTRS = _list{} fme_geometry{} inNetwork{} inNetwork{}.xlink_href
    REMOVE_ATTRS = _list_index,_list{0},fme_geometry{0},inNetwork{0}.xlink_href,inspireId.Identifier.localId,path_directory_unix,path_directory_windows,path_extension,path_rootname,path_type,path_unix,path_windows,telecommunicationsCableMaterialType.xlink_href,buismateriaalType.xlink_href,count,link_element_count
    -> AttributeRenamer_16
AttributeRenamer_16
    ATTR_TABLE:
      RENAME_SET_DEFAULT currentStatus.xlink_href > status
      RENAME_SET_DEFAULT extraGeometrie.xlink_href > geometrie_id
    KEEP_RENAMED_ONLY = no
    MISSING_INPUT_ATTRS = REMOVE
    -> Junction_3
AttributeExposer_11
    ATTR_LIST = inNetwork{0}.xlink_href,currentStatus.xlink_href,validFrom,verticalPosition,inspireId.Identifier.localId,poleHeight
    -> StringReplacer_36
StringReplacer_36
    CASE = NO
    FIND_TEXT = http://inspire.ec.europa.eu/codelist/ConditionOfFacilityValue/
    NO_MATCH = _FME_NO_OP_
    REGEXP = NO
    SRC_ATTRS = currentStatus.xlink_href
    -> ListElementCounter_11
ListElementCounter_11
    CNT_ATTR = link_element_count
    LIST_NAME = inNetwork{}
    -> AttributeCreator_18
AttributeCreator_18
    ATTR_TABLE:
      SET_TO count = @Evaluate(@Value(link_element_count)-1)
      SET_TO LinkId = @Value(inspireId.Identifier.localId)@Value(count)
      SET_TO NetwerkId = @Value(inNetwork{0}.xlink_href)
    -> StringReplacer_35
StringReplacer_35
    CASE = NO
    FIND_TEXT = nl.imkl-
    NO_MATCH = _FME_NO_OP_
    REGEXP = NO
    SRC_ATTRS = NetwerkId,LinkId
    -> AttributeRemover_17
AttributeRemover_17
    LIST_ATTRS = _list{} fme_geometry{} inNetwork{} inNetwork{}.xlink_href
    REMOVE_ATTRS = _list_index,_list{0},fme_geometry{0},inNetwork{0}.xlink_href,inspireId.Identifier.localId,path_directory_unix,path_directory_windows,path_extension,path_rootname,path_type,path_unix,path_windows,count,link_element_count
    -> AttributeRenamer_14
AttributeRenamer_14
    ATTR_TABLE:
      RENAME_SET_DEFAULT currentStatus.xlink_href > status
      RENAME_SET_DEFAULT extraGeometrie.xlink_href > geometrie_id
    KEEP_RENAMED_ONLY = no
    MISSING_INPUT_ATTRS = REMOVE
    -> Junction_3
AttributeExposer_12
    ATTR_LIST = inNetwork{0}.xlink_href,currentStatus.xlink_href,validFrom,verticalPosition,inspireId.Identifier.localId,extraGeometrie.xlink_href,label,bovengrondsZichtbaar
    -> StringReplacer_5
StringReplacer_5
    CASE = NO
    FIND_TEXT = http://inspire.ec.europa.eu/codelist/ConditionOfFacilityValue/
    NO_MATCH = _FME_NO_OP_
    REGEXP = NO
    SRC_ATTRS = currentStatus.xlink_href
    -> ListElementCounter_2
ListElementCounter_2
    CNT_ATTR = link_element_count
    LIST_NAME = inNetwork{}
    -> AttributeCreator_19
AttributeCreator_19
    ATTR_TABLE:
      SET_TO count = @Evaluate(@Value(link_element_count)-1)
      SET_TO LinkId = @Value(inspireId.Identifier.localId)@Value(count)
      SET_TO NetwerkId = @Value(inNetwork{0}.xlink_href)
    -> StringReplacer_4
StringReplacer_4
    CASE = NO
    FIND_TEXT = nl.imkl-
    NO_MATCH = _FME_NO_OP_
    REGEXP = NO
    SRC_ATTRS = NetwerkId,LinkId
    -> AttributeRemover_5
AttributeRemover_5
    LIST_ATTRS = _list{} fme_geometry{} inNetwork{} inNetwork{}.xlink_href
    REMOVE_ATTRS = _list_index,_list{0},fme_geometry{0},inNetwork{0}.xlink_href,inspireId.Identifier.localId,path_directory_unix,path_directory_windows,path_extension,path_rootname,path_type,path_unix,path_windows,count,link_element_count
    -> AttributeRenamer_3
AttributeRenamer_3
    ATTR_TABLE:
      RENAME_SET_DEFAULT currentStatus.xlink_href > status
      RENAME_SET_DEFAULT extraGeometrie.xlink_href > geometrie_id
    KEEP_RENAMED_ONLY = no
    MISSING_INPUT_ATTRS = REMOVE
    -> Junction_3
AttributeExposer_13
    ATTR_LIST = inNetwork{0}.xlink_href,currentStatus.xlink_href,validFrom,verticalPosition,inspireId.Identifier.localId
    -> StringReplacer_9
StringReplacer_9
    CASE = NO
    FIND_TEXT = http://inspire.ec.europa.eu/codelist/ConditionOfFacilityValue/
    NO_MATCH = _FME_NO_OP_
    REGEXP = NO
    SRC_ATTRS = currentStatus.xlink_href
    -> ListElementCounter_3
ListElementCounter_3
    CNT_ATTR = link_element_count
    LIST_NAME = inNetwork{}
    -> AttributeCreator_20
AttributeCreator_20
    ATTR_TABLE:
      SET_TO count = @Evaluate(@Value(link_element_count)-1)
      SET_TO LinkId = @Value(inspireId.Identifier.localId)@Value(count)
      SET_TO NetwerkId = @Value(inNetwork{0}.xlink_href)
    -> StringReplacer_8
StringReplacer_8
    CASE = NO
    FIND_TEXT = nl.imkl-
    NO_MATCH = _FME_NO_OP_
    REGEXP = NO
    SRC_ATTRS = NetwerkId,LinkId
    -> AttributeRemover_7
AttributeRemover_7
    LIST_ATTRS = _list{} fme_geometry{} inNetwork{} inNetwork{}.xlink_href
    REMOVE_ATTRS = _list_index,_list{0},fme_geometry{0},inNetwork{0}.xlink_href,inspireId.Identifier.localId,path_directory_unix,path_directory_windows,path_extension,path_rootname,path_type,path_unix,path_windows,count,link_element_count
    -> AttributeRenamer_4
AttributeRenamer_4
    ATTR_TABLE = RENAME_SET_DEFAULT currentStatus.xlink_href > status
    KEEP_RENAMED_ONLY = no
    MISSING_INPUT_ATTRS = REMOVE
    -> Junction_3
AttributeExposer_14
    ATTR_LIST = inNetwork{0}.xlink_href,currentStatus.xlink_href,validFrom,verticalPosition,inspireId.Identifier.localId,geoNauwkeurigheidXY.xlink_href,label,rotatiehoekSymbool
    -> StringReplacer_12
StringReplacer_12
    CASE = NO
    FIND_TEXT = http://definities.geostandaarden.nl/imkl2015/id/waarde/NauwkeurigheidXYvalue/
    NO_MATCH = _FME_NO_OP_
    REGEXP = NO
    SRC_ATTRS = geoNauwkeurigheidXY.xlink_href
    -> StringReplacer_11
StringReplacer_11
    CASE = NO
    FIND_TEXT = http://inspire.ec.europa.eu/codelist/ConditionOfFacilityValue/
    NO_MATCH = _FME_NO_OP_
    REGEXP = NO
    SRC_ATTRS = currentStatus.xlink_href
    -> ListElementCounter_4
ListElementCounter_4
    CNT_ATTR = link_element_count
    LIST_NAME = inNetwork{}
    -> AttributeCreator_21
AttributeCreator_21
    ATTR_TABLE:
      SET_TO count = @Evaluate(@Value(link_element_count)-1)
      SET_TO LinkId = @Value(inspireId.Identifier.localId)@Value(count)
      SET_TO NetwerkId = @Value(inNetwork{0}.xlink_href)
    -> StringReplacer_10
StringReplacer_10
    CASE = NO
    FIND_TEXT = nl.imkl-
    NO_MATCH = _FME_NO_OP_
    REGEXP = NO
    SRC_ATTRS = NetwerkId,LinkId
    -> AttributeRemover_8
AttributeRemover_8
    LIST_ATTRS = _list{} fme_geometry{} inNetwork{} inNetwork{}.xlink_href
    REMOVE_ATTRS = _list_index,_list{0},fme_geometry{0},inNetwork{0}.xlink_href,inspireId.Identifier.localId,path_directory_unix,path_directory_windows,path_extension,path_rootname,path_type,path_unix,path_windows,count,link_element_count
    -> AttributeRenamer_5
AttributeRenamer_5
    ATTR_TABLE:
      RENAME_SET_DEFAULT currentStatus.xlink_href > status
      RENAME_SET_DEFAULT geoNauwkeurigheidXY.xlink_href > geoNauwkeurigheidXY
    KEEP_RENAMED_ONLY = no
    MISSING_INPUT_ATTRS = REMOVE
    -> Junction_3
AttributeExposer_15
    ATTR_LIST = inNetwork{0}.xlink_href,identificatie.NEN3610ID.lokaalID,extraInfoType.xlink_href,bestandMediaType.xlink_href,bestandLocatie
    -> StringReplacer_14
StringReplacer_14
    CASE = NO
    FIND_TEXT = http://definities.geostandaarden.nl/imkl2015/id/waarde/ExtraDetailInfoTypeValue/
    NO_MATCH = _FME_NO_OP_
    REGEXP = NO
    SRC_ATTRS = extraInfoType.xlink_href
    -> StringReplacer_15
StringReplacer_15
    CASE = NO
    FIND_TEXT = http://definities.geostandaarden.nl/imkl2015/id/waarde/BestandMediaTypeValue/
    NO_MATCH = _FME_NO_OP_
    REGEXP = NO
    SRC_ATTRS = bestandMediaType.xlink_href
    -> ListElementCounter_5
ListElementCounter_5
    CNT_ATTR = link_element_count
    LIST_NAME = inNetwork{}
    -> AttributeCreator_22
AttributeCreator_22
    ATTR_TABLE:
      SET_TO count = @Evaluate(@Value(link_element_count)-1)
      SET_TO LinkId = @Value(identificatie.NEN3610ID.lokaalID)@Value(count)
      SET_TO NetwerkId = @Value(inNetwork{0}.xlink_href)
    -> StringReplacer_13
StringReplacer_13
    CASE = NO
    FIND_TEXT = nl.imkl-
    NO_MATCH = _FME_NO_OP_
    REGEXP = NO
    SRC_ATTRS = NetwerkId,LinkId
    -> AttributeRemover_9
AttributeRemover_9
    LIST_ATTRS = _list{} fme_geometry{} inNetwork{} inNetwork{}.xlink_href
    REMOVE_ATTRS = _list_index,_list{0},fme_geometry{0},inNetwork{0}.xlink_href,path_directory_unix,path_directory_windows,path_extension,path_rootname,path_type,path_unix,path_windows,link_element_count,identificatie.NEN3610ID.lokaalID
    -> AttributeRenamer_6
AttributeRenamer_6
    ATTR_TABLE:
      RENAME_SET_DEFAULT extraInfoType.xlink_href > extraInfoType
      RENAME_SET_DEFAULT bestandMediaType.xlink_href > bestandMediaType
    KEEP_RENAMED_ONLY = no
    MISSING_INPUT_ATTRS = REMOVE
    -> Junction_3
AttributeExposer_17
    ATTR_LIST = inNetwork{0}.xlink_href,beginLifespanVersion,diepteAangrijpingspunt.xlink_href,diepteNauwkeurigheid.xlink_href,dieptePeil,identificatie.NEN3610ID.lokaalID
    -> StringReplacer_20
StringReplacer_20
    CASE = NO
    FIND_TEXT = http://definities.geostandaarden.nl/imkl2015/id/waarde/DiepteAangrijpingspuntValue/
    NO_MATCH = _FME_NO_OP_
    REGEXP = NO
    SRC_ATTRS = diepteAangrijpingspunt.xlink_href
    -> StringReplacer_21
StringReplacer_21
    CASE = NO
    FIND_TEXT = http://definities.geostandaarden.nl/imkl2015/id/waarde/NauwkeurigheidDiepteValue/
    NO_MATCH = _FME_NO_OP_
    REGEXP = NO
    SRC_ATTRS = diepteNauwkeurigheid.xlink_href
    -> ListElementCounter_6
ListElementCounter_6
    CNT_ATTR = link_element_count
    LIST_NAME = inNetwork{}
    -> AttributeCreator_24
AttributeCreator_24
    ATTR_TABLE:
      SET_TO count = @Evaluate(@Value(link_element_count)-1)
      SET_TO LinkId = @Value(identificatie.NEN3610ID.lokaalID)@Value(count)
      SET_TO NetwerkId = @Value(inNetwork{0}.xlink_href)
    -> StringReplacer_19
StringReplacer_19
    CASE = NO
    FIND_TEXT = nl.imkl-
    NO_MATCH = _FME_NO_OP_
    REGEXP = NO
    SRC_ATTRS = NetwerkId,LinkId
    -> AttributeRemover_11
AttributeRemover_11
    LIST_ATTRS = _list{} fme_geometry{} inNetwork{} inNetwork{}.xlink_href
    REMOVE_ATTRS = _list_index,_list{0},fme_geometry{0},inNetwork{0}.xlink_href,path_directory_unix,path_directory_windows,path_extension,path_rootname,path_type,path_unix,path_windows,identificatie.NEN3610ID.lokaalID,count,link_element_count
    -> AttributeRenamer_8
AttributeRenamer_8
    ATTR_TABLE:
      RENAME_SET_DEFAULT beginLifespanVersion > registratiedatum
      RENAME_SET_DEFAULT diepteAangrijpingspunt.xlink_href > diepteAangrijpingspunt
      RENAME_SET_DEFAULT diepteNauwkeurigheid.xlink_href > diepteNauwkeurigheid
    KEEP_RENAMED_ONLY = no
    MISSING_INPUT_ATTRS = REMOVE
    -> Junction_3
AttributeExposer_19
    ATTR_LIST = inNetwork{0}.xlink_href,beginLifespanVersion,identificatie.NEN3610ID.lokaalID,label,labelpositie.Labelpositie.aangrijpingHorizontaal.xlink_href,labelpositie.Labelpositie.aangrijpingVerticaal.xlink_href,maatvoeringsType.xlink_href,rotatiehoek
    -> StringReplacer_27
StringReplacer_27
    CASE = NO
    FIND_TEXT = http://definities.geostandaarden.nl/imkl2015/id/waarde/LabelpositieValue/
    NO_MATCH = _FME_NO_OP_
    REGEXP = NO
    SRC_ATTRS = labelpositie.Labelpositie.aangrijpingHorizontaal.xlink_href
    -> StringReplacer_28
StringReplacer_28
    CASE = NO
    FIND_TEXT = http://definities.geostandaarden.nl/imkl2015/id/waarde/LabelpositieValue/
    NO_MATCH = _FME_NO_OP_
    REGEXP = NO
    SRC_ATTRS = labelpositie.Labelpositie.aangrijpingVerticaal.xlink_href
    -> StringReplacer_29
StringReplacer_29
    CASE = NO
    FIND_TEXT = http://definities.geostandaarden.nl/imkl2015/id/waarde/MaatvoeringsTypeValue/
    NO_MATCH = _FME_NO_OP_
    REGEXP = NO
    SRC_ATTRS = maatvoeringsType.xlink_href
    -> ListElementCounter_8
ListElementCounter_8
    CNT_ATTR = link_element_count
    LIST_NAME = inNetwork{}
    -> AttributeCreator_26
AttributeCreator_26
    ATTR_TABLE:
      SET_TO count = @Evaluate(@Value(link_element_count)-1)
      SET_TO LinkId = @Value(identificatie.NEN3610ID.lokaalID)
      SET_TO NetwerkId = @Value(inNetwork{0}.xlink_href)
    -> StringReplacer_26
StringReplacer_26
    CASE = NO
    FIND_TEXT = nl.imkl-
    NO_MATCH = _FME_NO_OP_
    REGEXP = NO
    SRC_ATTRS = NetwerkId,LinkId
    -> AttributeRemover_13
AttributeRemover_13
    LIST_ATTRS = _list{} fme_geometry{} inNetwork{} inNetwork{}.xlink_href
    REMOVE_ATTRS = _list_index,_list{0},fme_geometry{0},inNetwork{0}.xlink_href,path_directory_unix,path_directory_windows,path_extension,path_rootname,path_type,path_unix,path_windows,count,link_element_count
    -> AttributeRenamer_9
AttributeRenamer_9
    ATTR_TABLE:
      RENAME_SET_DEFAULT beginLifespanVersion > registratiedatum
      RENAME_SET_DEFAULT labelpositie.Labelpositie.aangrijpingHorizontaal.xlink_href > labelPositieHorizontaal
      RENAME_SET_DEFAULT labelpositie.Labelpositie.aangrijpingVerticaal.xlink_href > labelPositieVerticaal
      RENAME_SET_DEFAULT maatvoeringsType.xlink_href > maatvoeringsType
    KEEP_RENAMED_ONLY = no
    MISSING_INPUT_ATTRS = REMOVE
    -> Junction_3
AttributeExposer_16
    ATTR_LIST = beginLifespanVersion,identificatie.NEN3610ID.lokaalID,status.xlink_href,typeTopografischObject.xlink_href
    -> StringReplacer_17
StringReplacer_17
    CASE = NO
    FIND_TEXT = http://definities.geostandaarden.nl/imkl2015/id/waarde/EigenTopografieStatusValue/
    NO_MATCH = _FME_NO_OP_
    REGEXP = NO
    SRC_ATTRS = status.xlink_href
    -> StringReplacer_18
StringReplacer_18
    CASE = NO
    FIND_TEXT = http://definities.geostandaarden.nl/imkl2015/id/waarde/TopografischObjectTypeValue/
    NO_MATCH = _FME_NO_OP_
    REGEXP = NO
    SRC_ATTRS = typeTopografischObject.xlink_href
    -> AttributeCreator_23
AttributeCreator_23
    ATTR_TABLE = SET_TO LinkId = @Value(identificatie.NEN3610ID.lokaalID)
    -> StringReplacer_16
StringReplacer_16
    CASE = NO
    FIND_TEXT = nl.imkl-
    NO_MATCH = _FME_NO_OP_
    REGEXP = NO
    SRC_ATTRS = LinkId
    -> AttributeRemover_10
AttributeRemover_10
    REMOVE_ATTRS = _list_index,_list{0},fme_geometry{0},path_directory_unix,path_directory_windows,path_extension,path_rootname,path_type,path_unix,path_windows,identificatie.NEN3610ID.lokaalID
    -> AttributeRenamer_7
AttributeRenamer_7
    ATTR_TABLE:
      RENAME_SET_DEFAULT beginLifespanVersion > registratiedatum
      RENAME_SET_DEFAULT status.xlink_href > status
      RENAME_SET_DEFAULT typeTopografischObject.xlink_href > typeTopografischObject
    KEEP_RENAMED_ONLY = no
    MISSING_INPUT_ATTRS = REMOVE
    -> Junction_3
AttributeExposer_18
    ATTR_LIST = inNetwork{0}.xlink_href,annotatieType.xlink_href,beginLifespanVersion,identificatie.NEN3610ID.lokaalID,label,labelpositie.Labelpositie.aangrijpingHorizontaal.xlink_href,labelpositie.Labelpositie.aangrijpingVerticaal.xlink_href,rotatiehoek
    -> StringReplacer_23
StringReplacer_23
    CASE = NO
    FIND_TEXT = http://definities.geostandaarden.nl/imkl2015/id/waarde/LabelpositieValue/
    NO_MATCH = _FME_NO_OP_
    REGEXP = NO
    SRC_ATTRS = labelpositie.Labelpositie.aangrijpingHorizontaal.xlink_href
    -> StringReplacer_25
StringReplacer_25
    CASE = NO
    FIND_TEXT = http://definities.geostandaarden.nl/imkl2015/id/waarde/AnnotatieTypeValue/
    NO_MATCH = _FME_NO_OP_
    REGEXP = NO
    SRC_ATTRS = annotatieType.xlink_href
    -> StringReplacer_24
StringReplacer_24
    CASE = NO
    FIND_TEXT = http://definities.geostandaarden.nl/imkl2015/id/waarde/LabelpositieValue/
    NO_MATCH = _FME_NO_OP_
    REGEXP = NO
    SRC_ATTRS = labelpositie.Labelpositie.aangrijpingVerticaal.xlink_href
    -> ListElementCounter_7
ListElementCounter_7
    CNT_ATTR = link_element_count
    LIST_NAME = inNetwork{}
    -> AttributeCreator_25
AttributeCreator_25
    ATTR_TABLE:
      SET_TO count = @Evaluate(@Value(link_element_count)-1)
      SET_TO LinkId = @Value(identificatie.NEN3610ID.lokaalID)
      SET_TO NetwerkId = @Value(inNetwork{0}.xlink_href)
    -> StringReplacer_22
StringReplacer_22
    CASE = NO
    FIND_TEXT = nl.imkl-
    NO_MATCH = _FME_NO_OP_
    REGEXP = NO
    SRC_ATTRS = NetwerkId,LinkId
    -> AttributeRemover_12
AttributeRemover_12
    LIST_ATTRS = _list{} fme_geometry{} inNetwork{} inNetwork{}.xlink_href
    REMOVE_ATTRS = _list_index,_list{0},fme_geometry{0},inNetwork{0}.xlink_href,path_directory_unix,path_directory_windows,path_extension,path_rootname,path_type,path_unix,path_windows,count,link_element_count,identificatie.NEN3610ID.lokaalID
    -> AttributeRenamer_2
AttributeRenamer_2
    ATTR_TABLE:
      RENAME_SET_DEFAULT labelpositie.Labelpositie.aangrijpingHorizontaal.xlink_href > labelPositieHorizontaal
      RENAME_SET_DEFAULT labelpositie.Labelpositie.aangrijpingVerticaal.xlink_href > labelPositieVerticaal
      RENAME_SET_DEFAULT beginLifespanVersion > registratiedatum
      RENAME_SET_DEFAULT annotatieType.xlink_href > annotatieype
    KEEP_RENAMED_ONLY = no
    MISSING_INPUT_ATTRS = REMOVE
    -> Junction_3
AttributeExposer_20
    ATTR_LIST = inNetwork{0}.xlink_href,beginLifespanVersion,identificatie.NEN3610ID.lokaalID
    -> ListElementCounter_9
ListElementCounter_9
    CNT_ATTR = link_element_count
    LIST_NAME = inNetwork{}
    -> AttributeCreator_27
AttributeCreator_27
    ATTR_TABLE:
      SET_TO count = @Evaluate(@Value(link_element_count)-1)
      SET_TO LinkId = @Value(identificatie.NEN3610ID.lokaalID)
      SET_TO NetwerkId = @Value(inNetwork{0}.xlink_href)
    -> StringReplacer_30
StringReplacer_30
    CASE = NO
    FIND_TEXT = nl.imkl-
    NO_MATCH = _FME_NO_OP_
    REGEXP = NO
    SRC_ATTRS = NetwerkId,LinkId
    -> AttributeRemover_14
AttributeRemover_14
    LIST_ATTRS = _list{} fme_geometry{} inNetwork{} inNetwork{}.xlink_href
    REMOVE_ATTRS = _list_index,_list{0},fme_geometry{0},inNetwork{0}.xlink_href,path_directory_unix,path_directory_windows,path_extension,path_rootname,path_type,path_unix,path_windows,count,link_element_count,identificatie.NEN3610ID.lokaalID
    -> AttributeRenamer_10
AttributeRenamer_10
    ATTR_TABLE = RENAME_SET_DEFAULT beginLifespanVersion > registratiedatum
    KEEP_RENAMED_ONLY = no
    MISSING_INPUT_ATTRS = REMOVE
    -> Junction_3
AttributeExposer_21
    ATTR_LIST = inNetwork{0}.xlink_href,appurtenanceType.xlink_href,beginLifespanVersion,bovengrondsZichtbaar,currentStatus.xlink_href,geoNauwkeurigheidXY.xlink_href,inspireId.Identifier.localId,rotatiehoekSymbool,validFrom,verticalPosition
    -> StringReplacer_32
StringReplacer_32
    CASE = NO
    FIND_TEXT = http://inspire.ec.europa.eu/codelist/ElectricityAppurtenanceTypeValue/
    NO_MATCH = _FME_NO_OP_
    REGEXP = NO
    SRC_ATTRS = appurtenanceType.xlink_href
    -> StringReplacer_33
StringReplacer_33
    CASE = NO
    FIND_TEXT = http://inspire.ec.europa.eu/codelist/ConditionOfFacilityValue/
    NO_MATCH = _FME_NO_OP_
    REGEXP = NO
    SRC_ATTRS = currentStatus.xlink_href
    -> StringReplacer_34
StringReplacer_34
    CASE = NO
    FIND_TEXT = http://definities.geostandaarden.nl/imkl2015/id/waarde/NauwkeurigheidXYvalue/
    NO_MATCH = _FME_NO_OP_
    REGEXP = NO
    SRC_ATTRS = geoNauwkeurigheidXY.xlink_href
    -> StringReplacer_42
StringReplacer_42
    CASE = NO
    FIND_TEXT = http://definities.geostandaarden.nl/imkl2015/id/waarde/TelecommunicationsAppurtenanceTypeIMKLValue/
    NO_MATCH = _FME_NO_OP_
    REGEXP = NO
    SRC_ATTRS = appurtenanceType.xlink_href
    -> StringReplacer_43
StringReplacer_43
    CASE = NO
    FIND_TEXT = http://definities.geostandaarden.nl/imkl2015/id/waarde/ElectricityAppurtenanceTypeIMKLValue/
    NO_MATCH = _FME_NO_OP_
    REGEXP = NO
    SRC_ATTRS = appurtenanceType.xlink_href
    -> StringReplacer_44
StringReplacer_44
    CASE = NO
    FIND_TEXT = http://data.gwsw.nl/totaal/
    NO_MATCH = _FME_NO_OP_
    REGEXP = NO
    SRC_ATTRS = appurtenanceType.xlink_href
    -> StringReplacer_45
StringReplacer_45
    CASE = NO
    FIND_TEXT = http://definities.geostandaarden.nl/imkl2015/id/waarde/OilGasChemicalsAppurtenanceTypeIMKLValue/
    NO_MATCH = _FME_NO_OP_
    REGEXP = NO
    SRC_ATTRS = appurtenanceType.xlink_href
    -> StringReplacer_46
StringReplacer_46
    CASE = NO
    FIND_TEXT = http://definities.geostandaarden.nl/imkl2015/id/waarde/OverigAppurtenanceTypeIMKLValue/
    NO_MATCH = _FME_NO_OP_
    REGEXP = NO
    SRC_ATTRS = appurtenanceType.xlink_href
    -> StringReplacer_47
StringReplacer_47
    CASE = NO
    FIND_TEXT = http://definities.geostandaarden.nl/imkl2015/id/waarde/SewerAppurtenanceTypeIMKLValue/
    NO_MATCH = _FME_NO_OP_
    REGEXP = NO
    SRC_ATTRS = appurtenanceType.xlink_href
    -> StringReplacer_48
StringReplacer_48
    CASE = NO
    FIND_TEXT = http://definities.geostandaarden.nl/imkl2015/id/waarde/WaterAppurtenanceTypeIMKLValue/
    NO_MATCH = _FME_NO_OP_
    REGEXP = NO
    SRC_ATTRS = appurtenanceType.xlink_href
    -> StringReplacer_49
StringReplacer_49
    CASE = NO
    FIND_TEXT = http://inspire.ec.europa.eu/codelist/OilGasChemicalsAppurtenanceTypeValue/
    NO_MATCH = _FME_NO_OP_
    REGEXP = NO
    SRC_ATTRS = appurtenanceType.xlink_href
    -> StringReplacer_50
StringReplacer_50
    CASE = NO
    FIND_TEXT = http://inspire.ec.europa.eu/codelist/SewerAppurtenanceTypeValue/
    NO_MATCH = _FME_NO_OP_
    REGEXP = NO
    SRC_ATTRS = appurtenanceType.xlink_href
    -> StringReplacer_51
StringReplacer_51
    CASE = NO
    FIND_TEXT = http://inspire.ec.europa.eu/codelist/WaterAppurtenanceTypeValue/
    NO_MATCH = _FME_NO_OP_
    REGEXP = NO
    SRC_ATTRS = appurtenanceType.xlink_href
    -> ListElementCounter_10
ListElementCounter_10
    CNT_ATTR = link_element_count
    LIST_NAME = inNetwork{}
    -> AttributeCreator_28
AttributeCreator_28
    ATTR_TABLE:
      SET_TO count = @Evaluate(@Value(link_element_count)-1)
      SET_TO LinkId = @Value(inspireId.Identifier.localId)@Value(count)
      SET_TO NetwerkId = @Value(inNetwork{0}.xlink_href)
    -> StringReplacer_31
StringReplacer_31
    CASE = NO
    FIND_TEXT = nl.imkl-
    NO_MATCH = _FME_NO_OP_
    REGEXP = NO
    SRC_ATTRS = NetwerkId,LinkId
    -> AttributeRemover_15
AttributeRemover_15
    LIST_ATTRS = _list{} fme_geometry{} inNetwork{} inNetwork{}.xlink_href
    REMOVE_ATTRS = _list_index,_list{0},fme_geometry{0},inNetwork{0}.xlink_href,inspireId.Identifier.localId,path_directory_unix,path_directory_windows,path_extension,path_rootname,path_type,path_unix,path_windows,telecommunicationsCableMaterialType.xlink_href,buismateriaalType.xlink_href,count,link_element_count
    -> AttributeRenamer_11
AttributeRenamer_11
    ATTR_TABLE:
      RENAME_SET_DEFAULT currentStatus.xlink_href > status
      RENAME_SET_DEFAULT appurtenanceType.xlink_href > appurtenanceType
      RENAME_SET_DEFAULT beginLifespanVersion > registratiedatum
      RENAME_SET_DEFAULT geoNauwkeurigheidXY.xlink_href > geoNauwkeurigheidXY
    KEEP_RENAMED_ONLY = no
    MISSING_INPUT_ATTRS = REMOVE
    -> Junction_3
Note: Outputs alle losse onderdelen
Junction_3
    -> FeatureMerger_2 [REQUESTOR]

Bookmark: Voorbereiden output locatie
AttributeCreator_30
    ATTR_TABLE = SET_TO Output = $(FME_MF_DIR_USERTYPED)
    -> StringReplacer_3
StringReplacer_3
    CASE = NO
    FIND_TEXT = /
    NO_MATCH = _FME_NO_OP_
    REGEXP = NO
    REPLACE_TEXT = \
    SRC_ATTRS = Output
    -> AttributeSplitter_15
AttributeSplitter_15
    ATTR_NAME = path_filename
    DELIMITER = GI_gebiedsinformatielevering_
    DROP_EMPTY_PARTS = No
    LIST_NAME = _listName
    TRIM_COMMAND = trim
    TRIM_OPTION = Both
    -> AttributeSplitter_16
AttributeSplitter_16
    ATTR_NAME = _listName{1}
    DELIMITER = .xml
    DROP_EMPTY_PARTS = No
    LIST_NAME = _listName2
    TRIM_COMMAND = trim
    TRIM_OPTION = Both
    -> AttributeCreator_31
AttributeCreator_31
    ATTR_TABLE:
      SET_TO Output = @Value(Output)@Value(_listName2{0}).gpkg
      SET_TO Klic = Levering_@Value(_listName2{0})
    -> AttributeRenamer

Bookmark: Klic wegschrijven
FeatureWriter_2
    COORDSYS = EPSG:28992
    DATASET = $(Destination_writer)\@Value(Klic).gpkg
    DATASET_ATTR = _dataset
    FEATURE_TYPE_LIST_ATTR = _feature_types
    FORMAT = OGCGEOPACKAGE
    OGCGEOPACKAGE_COORDINATE_SYSTEM_GRANULARITY = FEATURE_TYPE
    OGCGEOPACKAGE_DATASET_TEMPLATE = $(KLIC_style_GPKG)
    OGCGEOPACKAGE_DESTINATION_DATASETTYPE_VALIDATION = Yes
    OGCGEOPACKAGE_ENCODE_FEATURE_TYPE_AND_ATTR_NAMES = YES
    OGCGEOPACKAGE_ENFORCE_GEOMETRY_COLUMN_CONSTRAINTS = YES
    OGCGEOPACKAGE_EXPOSE_PRIMARY_KEY_ATTRIBUTE = YES
    OGCGEOPACKAGE_OVERWRITE_DATASET = YES
    OGCGEOPACKAGE_TRANSACTION_SIZE = 5000
    OGCGEOPACKAGE_WRITE_NULLS = YES
    TOTAL_FEATURES_WRITTEN_ATTR = _total_features_written
    SUMMARY -> AttributeSplitter_19

FME custom transformer ZipExtractor
Extracts files archived in a zip file, and then outputs features for every extracted file and directory.
    Each resulting feature has two attributes storing full path string of an extracted file/directory - 
    "path_unix"
    (UNIX style) and 
    "path_windows"
    (Windows style), and also has an attribute that indicates the depth of the file/directory in the extracted directory hierarchy - 
    "path_depth" 
    (integer starting from 1).
    The features containing file path will be output through the File port, and the features containing directory path will be output through the Directory port. 
    All the extracted files will be saved into a subfolder under the folder specified with the "Destination Root Folder" parameter. The subfolder name will be the same as the source zip file name without extension. For example, if the source zip file name is 
    "data.zip"
    and the specified root folder path is 
    "C:\root"
    , extracted files will be saved into 
    "C:\root\data"
    .
    If the same name folder exists under the specified root folder, a number will be added to the destination subfolder name as suffix to differentiate from the existing folder, by default. e.g. 
    "C:\root\data_1"
    , 
    "C:\root\data_2"
    , and so on. 
    If you set "Yes" to the "Replace Existing Destination Subfolder" parameter, the existing subfolder and all files within it will be removed, and then the destination subfolder will be created newly.
    By default, this transformer will NOT unzip zip files that are archived (nested) in the source zip file. If you set "Yes" to the "Unzip Nested Zip Files Recursively" parameter, this transformer unzips all the nested zip files recursively.
    All attributes of the input feature will be propagated to the output features, but the geometry and coordinate system will not be preserved.
    If the specified source zip file or destination root folder is invalid, the input feature will be output through the <Rejected> port.
    Note: The Unzipper (FME Hub) can also be used to unzip a zip file. The ZipExtractor may be useful if you need to specify the destination root folder and/or to unzip nested zip file(s).
Parameters
    Source Zip File
    :
    Specify a zip file that should be extracted. The zip file name has to end with the extension ".zip" (case insensitive) by default, but optionally, you can also specify any extension(s) which this transformer should attempt to extract as a zip file. See the Allowable Source/Nested Zip File Extensions parameter.
    Destination Root Folder
    :
    Specify a folder in which a subfolder containing all extracted files should be created. If you leave this parameter blank, this transformer treats the folder containing the source zip file as the destination root folder.
    All the extracted files will be saved into a subfolder under the root folder. The subfolder name will be the same as the source zip file name without extension. For example, if the source zip file name is 
    "data.zip"
    and the specified root folder path is 
    "C:\root"
    , extracted files will be saved into 
    "C:\root\data"
    .
    Replace Existing Destination Subfolder
    :
    By default, a number will be added to the destination subfolder name as suffix if the same name folder exists under the spcified root folder. e.g. 
    "C:\root\data_1"
    , 
    "C:\root\data_2"
    , and so on. If you set "Yes" to this parameter, the existing subfolder and all files within it will be removed, and then the destination subfolder will be created newly. 
    Unzip Nested Zip Files Recursively
    :
    By default, this transformer will NOT unzip zip files that are archived (nested) in the source zip file. If you set "Yes" to this parameter, this transformer unzips all the nested zip files recursively.
    Preserve Nested Zip Files
    :
    By default, zip files nested in the source zip file will be removed after unzipping them, when the "Unzip Nested Zip Files Recursively" parameter is set to "Yes". If you set "Yes" to this parameter, the nested zip files will also be preserved.
    This parameter affects the result only when the "Unzip Nested Zip Files Recursively" parameter is set to "Yes". When the "Unzip Nested Zip Files Recursively" is set to "No", nested zip files always will be preserved regardless of this parameter.
    Allowable Source/Nested Zip File Extension(s)
    :
    By default, this transformer accepts only zip files whose name end with the extension ".zip" (case insensitive). However, if you want to extract zip files with other extension, you can specify allowable extention(s) via these parameters, with space-separated format when specifying two or more.
    Here, "Source Zip File" means that the top level zip file which would be set to the Source Zip File parameter; "Nested Zip File"means that internal zip file(s) which have been archived within the source zip file.
    If you leave the parameter field blank (it's the default), only ".zip" (case insensitive) will be allowable as zip file extension.
    Note that "zip" won't be allowable if you have set one or more extension other than ".zip" to the parameter. If you want to allow ".zip" and other extension(s) simultaneously, specify all possible extensions including ".zip" with the parameter.
    The leading dot "." of extensions can be omitted.

Parameters:
- ZIP_PATH =   # Source Zip File
- ROOT_FOLDER =   # Destination Root Folder
- REPLACE = No   # Replace Existing Destination Subfolder
- RECURSIVE = No   # Unzip Nested Zip Files Recursively
- PRESERVE = No   # Preserve Nested Zip Files
- EXT_S =   # Allowable Source Zip File Extension(s)
- EXT_N =   # Allowable Nested Zip File Extension(s)

Input (input)
    -> ParameterFetcher
ParameterFetcher
    ATTR_LIST = __unzipper.zip_path {$(ZIP_PATH)} __unzipper.root_folder {$(ROOT_FOLDER)} __unzipper.replace {$(REPLACE)} __unzipper.recursive {$(RECURSIVE)} __unzipper.preserve {$(PRESERVE)} __unzipper.ext_s {$(EXT_S)} __unzipper.ext_n {$(EXT_N)}
    -> PythonCaller
PythonCaller
    HIDE_ATTRIBUTES = __unzipper.ext_n __unzipper.zip_path __unzipper.ext_s __unzipper.replace __unzipper.recursive __unzipper.root_folder __unzipper.preserve
    NEW_ATTRIBUTES = path_unix path_windows path_depth __unzipper.flag _error_message
    PYTHONSOURCE:
      # 2016-01-21, Takashi Iijima, Original Implementation
      # 2016-01-23, Takashi Iijima, Updated:
      # - added function to check file extension to prevent extracting non-archiver zip files. e.g. Excel (*.xlsx) etc.
      # - added codes to create desitnation root folder if it is specified but doesn't exist.
      # - added option to preserve nested zip files after unzipping them.
      # - added "path_depth" attribute to output features.
      # 2016-01-25, Takashi Iijima, Updated to trim leading and trailing whitespaces of specified path strings.
      # 2018-06-14, Takashi Iijima, Added Allowable Source/Nested Zip File Extention(s) parameter.
      # 2019-01-13, Takashi Iijima, Fixed the destination folder name derived from zip filename which has non-4-letters suffix (e.g. ".xlsx").
      # 2020-01-13, Takashi Iijima, Changed Default Python Interpreter to 3.6+, saved with FME 2017.1.2.1

      import fmeobjects, zipfile, os

      class ZipExtractor(object):
          def __init__(self):
              self.logger = fmeobjects.FMELogFile()
              self.kFlagFile = 'file'
              self.kFlagDirectory = 'directory'
              self.kFlagReject = 'reject'
              self.kFlagTerminate = 'terminate'
              self.zipExtS = set(['.zip']) # Filename extensions source (root) zip files
              self.zipExtN = set(['.zip']) # Filename extensions for archived (descendant) zip files

          # Returns the number of characters of the zip file extension
          # if the path points a valid zip file, 0 otherwise.
          def zipExtLen(self, path, zipExt):
              _, ext = os.path.splitext(path)
              return len(ext) if (ext.lower() in zipExt and zipfile.is_zipfile(path)) else 0

          def input(self, feature):
              # Retrieve parameter values from feature attributes, then remove the attributes.
              # Zip path may end with a path separator if extracted by the FilenamePartExtractor as "_dirpath".
              zipPath = feature.getAttribute('__unzipper.zip_path').strip().rstrip('\\/')
              rootFolder = feature.getAttribute('__unzipper.root_folder').strip()
              replace = (feature.getAttribute('__unzipper.replace') == 'Yes')
              self.recursive = (feature.getAttribute('__unzipper.recursive') == 'Yes')
              self.preserve = (feature.getAttribute('__unzipper.preserve') == 'Yes')
              extS = set(feature.getAttribute('__unzipper.ext_s').split())
              extN = set(feature.getAttribute('__unzipper.ext_n').split())
              feature.removeAttrsWithPrefix('__unzipper.')

              if extS:
                  self.zipExtS = set([(e if e.startswith('.') else ('.%s' % e)).lower() for e in extS])
              if extN:
                  self.zipExtN = set([(e if e.startswith('.') else ('.%s' % e)).lower() for e in extN])

              # If destination root folder is specified but doesn't exist, try creating the directory.
              isRootValid = True
              if rootFolder and not os.path.exists(rootFolder):
                  try:
                      os.makedirs(rootFolder)
                  except:
                      isRootValid = False

              # If specified zip file or destination root folder is invalid, reject the input feature.
              if not os.path.exists(zipPath) \
                  or self.zipExtLen(zipPath, self.zipExtS) == 0 \
                  or not isRootValid:
                  msg = 'Specified zip file or destination root folder is invalid.'
                  self.logger.logMessageString(msg, fmeobjects.FME_ERROR)
                  feature.setAttribute('_error_message', msg)
                  feature.setAttribute('__unzipper.flag', self.kFlagReject)
                  self.pyoutput(feature)
                  return

              # Define destination folder path: <root folder>/<source zip file name without extension>
              # If root folder is not specified, treat the folder containing source zip file as root folder.
              zipPath = os.path.abspath(zipPath)
              zipFolder, zipName = os.path.split(zipPath)
              rootName, _ = os.path.splitext(zipName)
              destFolder = os.path.join(os.path.abspath(rootFolder) if rootFolder else zipFolder, rootName)

              try:
                  # If the destination folder exists,
                  # - remove the existing folder and all files within it when REPLACE is set to Yes,
                  # - add suffix to the folder path when REPLACE is set to No.
                  if os.path.exists(destFolder):
                      if replace:
                          for dirpath, dirs, files in os.walk(destFolder, topdown=False):
                              for name in files:
                                  os.remove(os.path.join(dirpath, name))
                              for name in dirs:
                                  os.rmdir(os.path.join(dirpath, name))
                          os.rmdir(destFolder)
                      else:
                          format, n = '%s_%d', 1
                          while os.path.exists(format % (destFolder, n)): n += 1
                          destFolder = format % (destFolder, n)

                  # Extract the zip file and output features containing extracted file/directory path.
                  self.pathInfos = [] # tuples list - (file or directory path, flag: 'file' or 'directory', depth)
                  self.extract(zipPath, destFolder, 1)
                  for path, flag, depth in self.pathInfos:
                      feat = feature.cloneAttributes()
                      feat.setAttribute('path_unix', path.replace('\\', '/'))
                      feat.setAttribute('path_windows', path.replace('/', '\\'))
                      feat.setAttribute('path_depth', depth)
                      feat.setAttribute('__unzipper.flag', flag)
                      self.pyoutput(feat)

              except Exception as ex:
                  msg = 'Unexpected error: %s' % ex
                  self.logger.logMessageString(msg, fmeobjects.FME_ERROR)
                  feature.setAttribute('_error_message', msg)
                  feature.setAttribute('__unzipper.flag', self.kFlagTerminate)
                  self.pyoutput(feature)

          # Extract a zip file.
          def extract(self, zipPath, destPath, depth):
              with zipfile.ZipFile(zipPath) as z: z.extractall(destPath)
              self.findFiles(destPath, depth)

          # Find and collect extracted file/directory paths.
          def findFiles(self, dirPath, depth):
              self.pathInfos.append((dirPath, self.kFlagDirectory, depth))
              depth += 1
              for fname in os.listdir(dirPath):
                  path = os.path.join(dirPath, fname)
                  if os.path.isdir(path):
                      self.findFiles(path, depth)
                  elif self.recursive:
                      n = self.zipExtLen(path, self.zipExtN)
                      if n != 0:
                          if self.preserve:
                              self.pathInfos.append((path, self.kFlagFile, depth))
                              self.extract(path, os.path.join(dirPath, fname[:-n]), depth)
                          else:
                              self.extract(path, os.path.join(dirPath, fname[:-n]), depth)
                              os.remove(path)
                      else:
                          self.pathInfos.append((path, self.kFlagFile, depth))
                  else:
                      self.pathInfos.append((path, self.kFlagFile, depth))
    PYTHONSYMBOL = ZipExtractor
    -> AttributeFilter
AttributeFilter
    ATTR_NAME = __unzipper.flag
    ATTR_VALUES = file,directory,reject,terminate,<EMPTY>,<MISSING>,<NULL>,<UNFILTERED>
    file -> File (output)
    directory -> Directory (output)
    reject -> <Rejected> (output)
    terminate -> <Rejected> (output)
File (output)
Directory (output)
<Rejected> (output)
